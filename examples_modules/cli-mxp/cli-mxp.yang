module cli-mxp {

    namespace "http://fulgor.com/ns/cli-mxp";

    prefix "cli-mxp";

    description
      "CLI para configurar el muxponder de 40G";

    revision "2018-06-24" {
        description
          "Version 0.1.0";
    }

    
    typedef restricted-tipo-trafico {
      type enumeration {
        enum "otu2";
        enum "xge";
        }
    }

    typedef restricted-tipo-fec-linea {
      type enumeration {
        enum "gfec";
        enum "cerofec";
        }
    }

    typedef restricted-tipo-fec-cliente {
      type enumeration {
        enum "gfec_cliente";
        enum "cerofec_cliente";
        enum "nulofec_cliente";
        }
    }


    container mux-config {
        description
          "Parametros de la CLI";

        // @ MUXPONDER: ./muxponder --configuracion --[otu2|xge] --[gfec|cerofec] --[gfec_cliente|cerofec_cliente|nulofec_cliente] --canal "value" --potencia "value" --cd_compensacion "value"
        // ./muxponder --guardar --[otu2|xge] --[gfec|cerofec] --[gfec_cliente|cerofec_cliente|nulofec_cliente] --canal "value" --potencia "value" --cd_compensacion "value"
        
        leaf configuracion { 
            description
              "para configuración completa en modo muxponder (--configuracion) o guardar configuración en archivo de inicio (--guardar).";
            type string;
        }

        leaf tipo_trafico { 
            description
              "[otu2|xge] especifica el tipo de tráfico.";
            type restricted-tipo-trafico;
        }

        leaf tipo_fec_linea {
            description
              "[gfec|cerofec] especifica el uso de fec.";
            type restricted-tipo-fec-linea;
        }

        leaf tipo_fec_cliente {
            description
              "[gfec_cliente|cerofec_cliente|nulofec_cliente] especifica el uso de fec.";
            type restricted-tipo-fec-cliente;
        }

        leaf canal {
            description
              "canal especifica el canal óptico del módulo transponder.";
            type string;
        }

        leaf potencia {
            description
              "potencia especifica la potencia de salida del amplificador óptico (edfa).";
            type string;
        }

        leaf cd_compensacion {
            description
              "cd_compensacion especifica la compensación de dispersion cromática.";
            type string;
        }

        leaf edfa_output_power_config {
            description
              "Potencia de salida de EDFA.";
            type decimal64 {
                fraction-digits 1;
                range "0 .. 6";
            }
        }

        leaf warning_config {
            description
              "Un 0 indica que no se genera alarma por configuracion, 1 activa alarma por configuracion.";
            type int16 {
                range "0 .. 1000";
            }
        }

        list ports {
            key "port";
            leaf port {
                type int16{
                    range "0 .. 6";
                }
                mandatory true;
            }

            leaf neighbor {
                mandatory true;
                type string;
            }
            
            leaf port_neighbor {
                mandatory true;
                type string;
            }
        }

    }


    container mux-state {
        description "Representa a datos de estado del dispositivo.";

        config false;

        // float in C
        leaf fpga_temperature_state {
            description "Temperatura de la FPGA";
            type decimal64 {
                fraction-digits 2;
            }
        }

        leaf board_humidity_state {
            description "Humedad de la placa";
            type int16;
        }

        leaf edfa_output_power_state {
            description "Potencia de salida EDFA";
            type decimal64 {
                fraction-digits 1;
            }
        }

        // float in C
        leaf xfp_tx_power {
            description "TX power";
            type decimal64 {
                fraction-digits 2;
            }
        }

        // float in C
        leaf xfp_rx_power {
            description "RX power";
            type decimal64 {
                fraction-digits 2;
            }
        }

        leaf device_manufacturer {
            description "Fabricante del dispositivo";
            type string;
        }

        leaf device_swVersion {
            description "Version del SW";
            type string;
        }

        leaf device_hwVersion {
            description "Version del HW";
            type string;
        }

        leaf device_boardId {
            description "Identificador unico del dispositivo";
            type string;
        }



    }


    container mux-state-misc {
        description "Container para variables de tipo misc en monitor";
        config false;
        
        //txp_struct->txp_temperature[0]
        leaf temp_around {
            description "State de la variable temp_around";
            type string;
        }

        //txp_struct->txp_temperature[1]
        leaf temp_case {
            description "State de la variable temp_case";
            type string;
        }

        //txp_struct->txp_temperature[2]
        leaf temp_tx_laser {
            description "State de la variable temp_tx_laser";
            type string;
        }

        //txp_struct->txp_temperature[3]
        leaf temp_rx_laser {
            description "State de la variable temp_rx_laser";
            type string;
        }

        //txp_struct->txp_loss
        leaf loss {
            description "State de la variable loss";
            type string;
        }

        //txp_struct->txp_interrupt
        leaf interrupt {
            description "State de la variable interrupt";
            type string;
        }

        //ACA LAS OTRAS DOS HAY QUE MOVER

        //txp_struct->txp_tx_laser_itu_channel.fields.band
        leaf tx_laser_itu_band {
            description "State de la variable tx_laser_itu_band";
            type string;
        }

        //txp_struct->txp_tx_laser_itu_channel.fields.channel
        leaf tx_laser_itu_channel {
            description "State de la variable tx_laser_itu_channel";
            type string;
        }

        //txp_struct->txp_rx_laser_itu_channel.fields.band
        leaf rx_laser_itu_band {
            description "State de la variable rx_laser_itu_band";
            type string;
        }

        //txp_struct->txp_rx_laser_itu_channel.fields.channel
        leaf rx_laser_itu_channel {
            description "State de la variable rx_laser_itu_channel";
            type string;
        }

    }

    container mux-state-TX-RX-alarms {
        description "Container para variables de tipo alarmas TX/RX en monitor";
        config false;
        
        leaf EOL_ALM {
            type string;
        }

        leaf MOD_TEMP_ALM {
            type string;
        }

        leaf TX_OOA {
            type string;
        }

        leaf TX_LOF_ALM {
            type string;
        }

        leaf TX_DSC_ERR {
            type string;
        }
        
        leaf LS_WAV_ALM {
            type string;
        }
        
        leaf TX_ALM_INT {
            type string;
        }

        leaf LS_BIAS_ALM {
            type string;
        }

        leaf LS_TEMP_ALM {
            type string;
        }

        leaf TX_LOCK_ERR {
            type string;
        }

        leaf LS_POW_ALM {
            type string;
        }

        leaf MOD_BIAS_ALM {
            type string;
        }

        leaf LATCHED_TXFIFO_ERR {
            type string;
        }

        leaf RXALM_INT {
            type string;
        }

        leaf RXPOW_ALM {
            type string;
        }

        leaf RX_LOS {
            type string;
        }
        
        leaf RX_LOCK_ERR {
            type string;
        }

        leaf RXS {
            type string;
        }

        leaf PRBS_ERR_DET {
            type string;
        }
    }

        container mux-state-power {
            description "Container para variables de tipo power en monitor";
            config false;
        
            //txp_struct->txp_power_alarm.fields.psummary
            leaf PSUMMARY {
                description "State de la variable PSUMMARY";
                type string;
            }

            //txp_struct->txp_power_alarm.fields.p5vanalog
            leaf P5VANALOG {
                description "State de la variable P5VANALOG";
                type string;
            }

            //txp_struct->txp_power_alarm.fields.n5v2analog
            leaf N5V2ANALOG {
                description "State de la variable N5V2ANALOG";
                type string;
            }

            //txp_struct->txp_power_alarm.fields.p3p3vanalog
            leaf P3P3VANALOG {
                description "State de la variable P3P3VANALOG";
                type string;
            }

            //txp_struct->txp_power_alarm.fields.p3p3vdigital
            leaf P3P3VDIGITAL {
                description "State de la variable P3P3VDIGITAL";
                type string;
            }
            
            //txp_struct->txp_power_alarm.fields.lvdigital
            leaf LVDIGITAL {
                description "State de la variable LVDIGITAL";
                type string;
            }

            //txp_struct->txp_power_alarm.fields.n5p2vdigital
            leaf N5P2VDIGITAL {
                description "State de la variable N5P2VDIGITAL";
                type string;
            }
        }

    container mux-state-dsp {
            description "Container para variables de tipo dsp en monitor";
            config false;
        
            //txp_struct->txp_power_alarm.fields.psummary
            leaf DSP_running {
                description "State de la variable DSP running";
                type string;
            }

            //txp_struct->txp_power_alarm.fields.psummary
            leaf CONVERGED {
                description "State de la variable CONVERGED";
                type string;
            }

            //txp_struct->txp_power_alarm.fields.psummary
            leaf MSE_below_threshold {
                description "State de la variable MSE below threshold";
                type string;
            }

            //txp_struct->txp_power_alarm.fields.psummary
            leaf BCD_Enabled {
                description "State de la variable BCD_Enabled";
                type string;
            }

            //txp_struct->txp_power_alarm.fields.psummary
            leaf Coarse_Carrier_Lock {
                description "State de la variable Coarse Carrier Lock";
                type string;
            }

            //txp_struct->txp_power_alarm.fields.psummary
            leaf Collision {
                description "State de la variable Collision";
                type string;
            }

            //txp_struct->txp_power_alarm.fields.psummary
            leaf DSP_Initialized {
                description "State de la variable DSP Initialized";
                type string;
            }

            //txp_struct->txp_power_alarm.fields.psummary
            leaf Presence_of_light {
                description "State de la variable Presence of light";
                type string;
            }

            //txp_struct->txp_power_alarm.fields.psummary
            leaf Local_Oscillator_running {
                description "State de la variable Local_Oscillator_running";
                type string;
            }

            //txp_struct->txp_power_alarm.fields.psummary
            leaf Transmit_Laser_running {
                description "State de la variable Transmit Laser running";
                type string;
            }

            //txp_struct->txp_power_alarm.fields.psummary
            leaf MSE_XI {
                description "State de la variable MSE XI";
                type string;
            }

            //txp_struct->txp_power_alarm.fields.psummary
            leaf MSE_XQ {
                description "State de la variable MSE XQ";
                type string;
            }

            //txp_struct->txp_power_alarm.fields.psummary
            leaf MSE_YI {
                description "State de la variable MSE YI";
                type string;
            }

            //txp_struct->txp_power_alarm.fields.psummary
            leaf MSE_YQ {
                description "State de la variable MSE YQ";
                type string;
            }

            //txp_struct->txp_power_alarm.fields.psummary
            leaf BER_Estimate {
                description "State de la variable BER Estimate";
                type string;
            }

            //txp_struct->txp_power_alarm.fields.psummary
            leaf Min_Bulk_CD_Compensation_ps_nm {
                description "State de la variable Min. Bulk CD Compensation [ps/nm]";
                type string;
            }

            //txp_struct->txp_power_alarm.fields.psummary
            leaf Max_Bulk_CD_Compensation_ps_nm {
                description "State de la variable Max. Bulk CD Compensation [ps/nm]";
                type string;
            }

            //txp_struct->txp_power_alarm.fields.psummary
            leaf Step_Size_ps_nm {
                description "State de la variable Step Size [ps/nm]";
                type string;
            }

            //txp_struct->txp_power_alarm.fields.psummary
            leaf CD_Compensation_ps_nm {
                description "State de la variable CD Compensation [ps/nm]";
                type string;
            }
    }

    container mux-state-edfa {
        description "Container EDFA";
        config false;
        
        leaf POUT {
            description "State de la variable POUT";
            type string;
        }

        leaf PIN {
            description "State de la variable PIN";
            type string;
        }

        leaf Temp {
            description "State de la variable Temp";
            type string;
        }

        leaf LOS {
            description "State de la variable LOS";
            type string;
        }

        leaf LOP {
            description "State de la variable LOP";
            type string;
        }

        leaf Amp_stat {
            description "State de la variable Amp stat";
            type string;
        }
    }

    container mux-state-temp-hum {
        description "State temperatura y humedad";
        config false;
        
        leaf T41_Around {
            description "State de la variable T41_Around";
            type string;
        }

        leaf T41_TS0 {
            description "State de la variable T41_TS0";
            type string;
        }

        leaf T41_TS1 {
            description "State de la variable T41_TS1";
            type string;
        }

        leaf T41_TS2 {
            description "State de la variable T41_TS2";
            type string;
        }

        leaf FPGA {
            description "State de la variable FPGA";
            type string;
        }

        leaf BOARD_TEMP {
            description "State de la variable BOARD_TEMP";
            type string;
        }

        leaf BOARD_HUM {
            description "State de la variable BOARD_HUM";
            type string;
        }

    }

    container mux-state-XFP1 {
        description "State XFP1";
        config false;
        
        leaf Presence {
            description "State de la variable Presence";
            type string;
        }

        leaf Loss {
            description "State de la variable Loss";
            type string;
        }

        leaf Ready {
            description "State de la variable Ready";
            type string;
        }

        leaf Interrupt {
            description "State de la variable Interrupt";
            type string;
        }

        leaf Tx_Power_dBm {
            description "State de la variable Tx_Power_dBm";
            type string;
        }

        leaf Rx_Power_dBm {
            description "State de la variable Rx_Power_dBm";
            type string;
        }

        leaf Temp_c {
            description "State de la variable Temp_c";
            type string;
        }

        leaf Low_Tx_Power_Alarm {
            description "State de la variable Low_Tx_Power_Alarm";
            type string;
        }

        leaf High_Tx_Power_Alarm {
            description "State de la variable High_Tx_Power_Alarm";
            type string;
        }

        leaf Low_Rx_Power_Alarm {   
            description "State de la variable Low_Rx_Power_Alarm";
            type string;
        }

        leaf High_Rx_Power_Alarm {
            description "State de la variable High_Rx_Power_Alarm";
            type string;
        }

        leaf Rx_CDR_Loss_of_Lock {
            description "State de la variable Rx_CDR_Loss_of_Lock";
            type string;
        }

        leaf Tx_CDR_Loss_of_Lock {
            description "State de la variable Tx_CDR_Loss_of_Lock";
            type string;
        }

        leaf Laser_Fault {
            description "State de la variable Laser_Fault";
            type string;
        }
    }

    container mux-state-XFP2 {
        description "State XFP2";
        config false;
        
        leaf Presence {
            description "State de la variable Presence";
            type string;
        }

        leaf Loss {
            description "State de la variable Loss";
            type string;
        }

        leaf Ready {
            description "State de la variable Ready";
            type string;
        }

        leaf Interrupt {
            description "State de la variable Interrupt";
            type string;
        }

        leaf Tx_Power_dBm {
            description "State de la variable Tx_Power_dBm";
            type string;
        }

        leaf Rx_Power_dBm {
            description "State de la variable Rx_Power_dBm";
            type string;
        }

        leaf Temp_c {
            description "State de la variable Temp_c";
            type string;
        }

        leaf Low_Tx_Power_Alarm {
            description "State de la variable Low_Tx_Power_Alarm";
            type string;
        }

        leaf High_Tx_Power_Alarm {
            description "State de la variable High_Tx_Power_Alarm";
            type string;
        }

        leaf Low_Rx_Power_Alarm {   
            description "State de la variable Low_Rx_Power_Alarm";
            type string;
        }

        leaf High_Rx_Power_Alarm {
            description "State de la variable High_Rx_Power_Alarm";
            type string;
        }

        leaf Rx_CDR_Loss_of_Lock {
            description "State de la variable Rx_CDR_Loss_of_Lock";
            type string;
        }

        leaf Tx_CDR_Loss_of_Lock {
            description "State de la variable Tx_CDR_Loss_of_Lock";
            type string;
        }

        leaf Laser_Fault {
            description "State de la variable Laser_Fault";
            type string;
        }
    }

        container mux-state-XFP3 {
        description "State XFP3";
        config false;
        
        leaf Presence {
            description "State de la variable Presence";
            type string;
        }

        leaf Loss {
            description "State de la variable Loss";
            type string;
        }

        leaf Ready {
            description "State de la variable Ready";
            type string;
        }

        leaf Interrupt {
            description "State de la variable Interrupt";
            type string;
        }

        leaf Tx_Power_dBm {
            description "State de la variable Tx_Power_dBm";
            type string;
        }

        leaf Rx_Power_dBm {
            description "State de la variable Rx_Power_dBm";
            type string;
        }

        leaf Temp_c {
            description "State de la variable Temp_c";
            type string;
        }

        leaf Low_Tx_Power_Alarm {
            description "State de la variable Low_Tx_Power_Alarm";
            type string;
        }

        leaf High_Tx_Power_Alarm {
            description "State de la variable High_Tx_Power_Alarm";
            type string;
        }

        leaf Low_Rx_Power_Alarm {   
            description "State de la variable Low_Rx_Power_Alarm";
            type string;
        }

        leaf High_Rx_Power_Alarm {
            description "State de la variable High_Rx_Power_Alarm";
            type string;
        }

        leaf Rx_CDR_Loss_of_Lock {
            description "State de la variable Rx_CDR_Loss_of_Lock";
            type string;
        }

        leaf Tx_CDR_Loss_of_Lock {
            description "State de la variable Tx_CDR_Loss_of_Lock";
            type string;
        }

        leaf Laser_Fault {
            description "State de la variable Laser_Fault";
            type string;
        }
    }

        container mux-state-XFP4 {
        description "State XFP4";
        config false;
        
        leaf Presence {
            description "State de la variable Presence";
            type string;
        }

        leaf Loss {
            description "State de la variable Loss";
            type string;
        }

        leaf Ready {
            description "State de la variable Ready";
            type string;
        }

        leaf Interrupt {
            description "State de la variable Interrupt";
            type string;
        }

        leaf Tx_Power_dBm {
            description "State de la variable Tx_Power_dBm";
            type string;
        }

        leaf Rx_Power_dBm {
            description "State de la variable Rx_Power_dBm";
            type string;
        }

        leaf Temp_c {
            description "State de la variable Temp_c";
            type string;
        }

        leaf Low_Tx_Power_Alarm {
            description "State de la variable Low_Tx_Power_Alarm";
            type string;
        }

        leaf High_Tx_Power_Alarm {
            description "State de la variable High_Tx_Power_Alarm";
            type string;
        }

        leaf Low_Rx_Power_Alarm {   
            description "State de la variable Low_Rx_Power_Alarm";
            type string;
        }

        leaf High_Rx_Power_Alarm {
            description "State de la variable High_Rx_Power_Alarm";
            type string;
        }

        leaf Rx_CDR_Loss_of_Lock {
            description "State de la variable Rx_CDR_Loss_of_Lock";
            type string;
        }

        leaf Tx_CDR_Loss_of_Lock {
            description "State de la variable Tx_CDR_Loss_of_Lock";
            type string;
        }

        leaf Laser_Fault {
            description "State de la variable Laser_Fault";
            type string;
        }
    }

    container mux-optical-line-status {
        description "Para determinar estado del enlace";
        config false;
        
        leaf brctl_showstp_br0 {
            description "Devuelve la respuesta de ejecutar brctl showstp br0";
            type string;
        }
    }

    rpc mux-notify-activate {        
        description "RPC que activa la notificacion";
    }

    rpc mux-notify-deactivate {        
        description "RPC que desactiva la notificacion";
    }

    rpc mux-apply-config {        
        description "RPC que aplica los cambios --configuracion ";
        output {
            leaf respuesta-mux-apply-config {
                type string;
            }
        }
    }

    rpc mux-settings {        
        description "RPC que aplica los cambios --settings ";
        output {
            leaf respuesta-mux-settings {
                type string;
            }
        }
    }


    notification mux-notify {

        leaf INFO {
            type string;
            mandatory "true";
        }
    }

}
