module cli-mxp {

    namespace "http://fulgor.com/ns/cli-mxp";

    prefix "cli-mxp";

    description
      "CLI para configurar el muxponder de 40G";

    revision "2018-06-24" {
        description
          "Version 0.1.0";
    }

    container mux-config {
        description
          "Parametros de la CLI";

        // @ MUXPONDER: ./muxponder --configuracion --[otu2|xge] --[gfec|cerofec] --[gfec_cliente|cerofec_cliente|nulofec_cliente] --canal "value" --potencia "value" --cd_compensacion "value"
        // ./muxponder --guardar --[otu2|xge] --[gfec|cerofec] --[gfec_cliente|cerofec_cliente|nulofec_cliente] --canal "value" --potencia "value" --cd_compensacion "value"
        
        leaf configuracion {
            description
              "para configuración completa en modo muxponder (--configuracion) o guardar configuración en archivo de inicio (--guardar).";
            type string;
        }

        leaf tipo_trafico {
            description
              "[otu2|xge] especifica el tipo de tráfico.";
            type string;
        }

        leaf tipo_fec_linea {
            description
              "[gfec|cerofec] especifica el uso de fec.";
            type string;
        }

        leaf tipo_fec_cliente {
            description
              "[gfec_cliente|cerofec_cliente|nulofec_cliente] especifica el uso de fec.";
            type string;
        }

        leaf canal {
            description
              "canal especifica el canal óptico del módulo transponder.";
            type string;
        }

        leaf potencia {
            description
              "potencia especifica la potencia de salida del amplificador óptico (edfa).";
            type string;
        }

        leaf cd_compensacion {
            description
              "cd_compensacion especifica la compensación de dispersion cromática.";
            type string;
        }

        leaf edfa_output_power_config {
            description
              "Potencia de salida de EDFA.";
            type decimal64 {
                fraction-digits 2;
                range "4.0 .. 6.0";
            }
        }
    }


    container mux-state {
        description "Representa a datos de estado del dispositivo.";

        config false;

        leaf fpga_temperature_state {
            description "Temperatura de la FPGA";
            type decimal64 {
                fraction-digits 2;
            }
        }

        leaf board_humidity_state {
            description "Humedad de la placa";
            type int16;
        }

        leaf edfa_output_power_state {
            description "Potencia de salida EDFA";
            type decimal64 {
                fraction-digits 2;
            }
        }

    }


    rpc mux-apply {
        
        description "RPC que aplica la configuracion segun el string enviado";

        input {
            leaf comando {
                type string;
            }
        }

        output {
            leaf respuesta {
                type string;
            }
        }
    }



    notification mux-notify {
        container source {
            leaf ringtone {
                type string;
                mandatory "true";
            }
        }
    }

}
