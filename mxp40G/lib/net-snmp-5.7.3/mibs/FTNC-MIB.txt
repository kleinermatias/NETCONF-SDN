FTNC-MIB DEFINITIONS ::= BEGIN

IMPORTS
    MODULE-IDENTITY, OBJECT-TYPE, enterprises, Integer32, NOTIFICATION-TYPE
        FROM SNMPv2-SMI
        
    OBJECT-GROUP, MODULE-COMPLIANCE, NOTIFICATION-GROUP
        FROM SNMPv2-CONF;

fotonica MODULE-IDENTITY
    LAST-UPDATED    "201605110000Z"
    ORGANIZATION    "Fotonica"
    CONTACT-INFO    "info@fotonicacommunications.com"
    DESCRIPTION     "Fotonica Communications"

    REVISION        "201605110000Z"
    DESCRIPTION     "Initial revision."
::= { enterprises 43484 }

projects OBJECT IDENTIFIER ::= {fotonica 1 }
mxp OBJECT IDENTIFIER ::= {projects 1 }
mxpConfigMIB OBJECT IDENTIFIER ::= { mxp 1 }
mxpConfigMIBConformance OBJECT IDENTIFIER ::= { mxpConfigMIB 1 }
mxpConfigMIBCompliances   OBJECT IDENTIFIER ::= { mxpConfigMIBConformance 1 }
mxpConfigMIBGroups OBJECT IDENTIFIER ::= { mxpConfigMIBConformance 2 }
mxpConfigMIBObjects OBJECT IDENTIFIER ::= { mxpConfigMIB 2 }


mxpConfigCompliance MODULE-COMPLIANCE
    STATUS  current
    DESCRIPTION
            "The compliance statement for config entities which
            implement this MIB module."
    MODULE  -- this module
        MANDATORY-GROUPS { powerGroup, fanGroup, xfp1Group, xfp2Group, xfp3Group, xfp4Group, envGroup, edfaGroup, txpAlrmTxGroup, txpAlrmRxGroup, txpPowSupplyAlrmGroup, txpTempGroup, txpPowerGroup, txpChannelGroup, txpBandGroup, txpPhyspadGroup, txpDSPStatusGroup, txpDSPErrorsGroup, txpDSPCompensationGroup, mxpGroup }

    ::= { mxpConfigMIBCompliances 1 }

powerTable OBJECT-TYPE
	SYNTAX	SEQUENCE OF PowerEntry
	MAX-ACCESS	not-accessible
	STATUS	current
	DESCRIPTION	"A table containing information on Power supply."
::= { mxpConfigMIBObjects 1 }

powerEntry OBJECT-TYPE
	SYNTAX	PowerEntry
	MAX-ACCESS	not-accessible
	STATUS	current
	DESCRIPTION "An entry of the power table."
	INDEX	{ powerIndex }
::= { powerTable 1 }

PowerEntry ::= SEQUENCE { powerIndex OCTET STRING, powera OCTET STRING, powerb OCTET STRING }

powerIndex OBJECT-TYPE
    SYNTAX     OCTET STRING (SIZE(1..32))
    MAX-ACCESS not-accessible
    STATUS     current
    DESCRIPTION
            "The auxiliary variable used for identifying instances
            of the columnar objects in the powerTable."
    ::= { powerEntry 1 }

powera OBJECT-TYPE
	SYNTAX      OCTET STRING
	MAX-ACCESS  read-only
	STATUS      current
	DESCRIPTION "Power supply A status"
::= { powerEntry 2 }

powerb OBJECT-TYPE
	SYNTAX      OCTET STRING 
	MAX-ACCESS  read-only
	STATUS      current
	DESCRIPTION "Power supply B status"
::= { powerEntry 3 }

powerGroup OBJECT-GROUP
    OBJECTS { powera, powerb }
    STATUS  current
    DESCRIPTION
        "The powerGroup group groups objects power."
    ::= { mxpConfigMIBGroups 1 }



fanTable OBJECT-TYPE
	SYNTAX SEQUENCE OF FanEntry
	MAX-ACCESS not-accessible
	STATUS current
	DESCRIPTION "A table containing information on Fan."
::= { mxpConfigMIBObjects 2 }

fanEntry OBJECT-TYPE
	SYNTAX	FanEntry
	MAX-ACCESS	not-accessible
	STATUS	current
	DESCRIPTION "An entry of the fan table."
	INDEX	{ fanIndex }
::= { fanTable  1 }

FanEntry ::= SEQUENCE { fanIndex OCTET STRING, fan1 OCTET STRING, fan2 OCTET STRING, fan3 OCTET STRING, fan4 OCTET STRING, fan5 OCTET STRING }

fanIndex OBJECT-TYPE
	SYNTAX	OCTET STRING (SIZE(1..32))
	MAX-ACCESS	not-accessible
	STATUS	current
	DESCRIPTION "The auxiliary variable used for identifying instances
            of the columnar objects in the fanTable"
::= { fanEntry 1 }

fan1 OBJECT-TYPE
	SYNTAX      OCTET STRING
	MAX-ACCESS  read-only
	STATUS      current
	DESCRIPTION "Fan 1 status"
::= { fanEntry 2 }

fan2 OBJECT-TYPE
	SYNTAX      OCTET STRING
	MAX-ACCESS  read-only
	STATUS      current
	DESCRIPTION "Fan 2 status"
::= { fanEntry 3 }

fan3 OBJECT-TYPE
	SYNTAX      OCTET STRING
	MAX-ACCESS  read-only
	STATUS      current
	DESCRIPTION "Fan 3 status"
::= { fanEntry 4 }

fan4 OBJECT-TYPE
	SYNTAX      OCTET STRING
	MAX-ACCESS  read-only
	STATUS      current
	DESCRIPTION "Fan 4 status"
::= { fanEntry 5 }

fan5 OBJECT-TYPE
	SYNTAX      OCTET STRING
	MAX-ACCESS  read-only
	STATUS      current
	DESCRIPTION "Fan 5 status"
::= { fanEntry 6 }

fanGroup OBJECT-GROUP
    OBJECTS { fan1, fan2, fan3, fan4, fan5 }
    STATUS  current
    DESCRIPTION
        "The fanGroup group groups objects fan."
    ::= { mxpConfigMIBGroups 2 }



xfp1Table OBJECT-TYPE
	SYNTAX	SEQUENCE OF Xfp1Entry
	MAX-ACCESS	not-accessible
	STATUS	current
	DESCRIPTION "A table containing information on xfp1."
::= { mxpConfigMIBObjects 3 }

xfp1Entry OBJECT-TYPE
	SYNTAX Xfp1Entry
	MAX-ACCESS not-accessible
	STATUS current
	DESCRIPTION "An entry of the xfp1 table."
	INDEX	{ xfp1Index }
::= { xfp1Table 1 }

Xfp1Entry ::= SEQUENCE { xfp1Index OCTET STRING, xfp1Pres OCTET STRING, xfp1Loss OCTET STRING, xfp1Rdy OCTET STRING, xfp1Int OCTET STRING, xfp1TxPow OCTET STRING, xfp1RxPow OCTET STRING, xfp1Temp OCTET STRING, xfp1LowTxPow OCTET STRING, xfp1HighTxPow OCTET STRING, xfp1LowRxPow OCTET STRING, xfp1HighRxPow OCTET STRING, xfp1RxCdrLol OCTET STRING, xfp1TxCdrLol OCTET STRING, xfp1LasFault OCTET STRING }

xfp1Index OBJECT-TYPE
	SYNTAX OCTET STRING (SIZE(1..32))
	MAX-ACCESS not-accessible
	STATUS current
	DESCRIPTION "Reference Index for each observed process."
::= { xfp1Entry 1 }

xfp1Pres OBJECT-TYPE
	SYNTAX OCTET STRING
	MAX-ACCESS read-only
	STATUS current
	DESCRIPTION "XFP1 Presence"
::= { xfp1Entry 2 }

xfp1Loss OBJECT-TYPE
	SYNTAX OCTET STRING 
	MAX-ACCESS read-only
	STATUS current
	DESCRIPTION "XFP1 Loss of Signal Indicator"
::= { xfp1Entry 3 }

xfp1Rdy OBJECT-TYPE
	SYNTAX OCTET STRING 
	MAX-ACCESS read-only
	STATUS current
	DESCRIPTION "XFP1 Ready"
::= { xfp1Entry 4 }

xfp1Int OBJECT-TYPE
	SYNTAX OCTET STRING 
	MAX-ACCESS read-only
	STATUS current
	DESCRIPTION "XFP1 Interruption signal"
::= { xfp1Entry 5 }

xfp1TxPow OBJECT-TYPE
	SYNTAX OCTET STRING 
	MAX-ACCESS read-only
	STATUS current
	DESCRIPTION "XFP1 TX Power"
::= { xfp1Entry 6 }

xfp1RxPow OBJECT-TYPE
	SYNTAX OCTET STRING 
	MAX-ACCESS read-only
	STATUS current
	DESCRIPTION "XFP1 RX Power"
::= { xfp1Entry 7 }

xfp1Temp OBJECT-TYPE
	SYNTAX OCTET STRING 
	MAX-ACCESS read-only
	STATUS current
	DESCRIPTION "XFP1 Temperature"
::= { xfp1Entry 8 }

xfp1LowTxPow OBJECT-TYPE
	SYNTAX OCTET STRING 
	MAX-ACCESS read-only
	STATUS current
	DESCRIPTION "XFP1 Low TX Power Alarm"
::= { xfp1Entry 9 }

xfp1HighTxPow OBJECT-TYPE
	SYNTAX OCTET STRING 
	MAX-ACCESS read-only
	STATUS current
	DESCRIPTION "XFP1 High TX Power Alarm"
::= { xfp1Entry 10 }

xfp1LowRxPow OBJECT-TYPE
	SYNTAX OCTET STRING 
	MAX-ACCESS read-only
	STATUS current
	DESCRIPTION "XFP1 High RX Power Alarm"
::= { xfp1Entry 11 }

xfp1HighRxPow OBJECT-TYPE
	SYNTAX OCTET STRING 
	MAX-ACCESS read-only
	STATUS current
	DESCRIPTION "XFP1 High RX Power Alarm"
::= { xfp1Entry 12 }

xfp1RxCdrLol OBJECT-TYPE
	SYNTAX OCTET STRING 
	MAX-ACCESS read-only
	STATUS current
	DESCRIPTION "XFP1 RX Loss of Lock Alarm"
::= { xfp1Entry 13 }

xfp1TxCdrLol OBJECT-TYPE
	SYNTAX OCTET STRING 
	MAX-ACCESS read-only
	STATUS current
	DESCRIPTION "XFP1 TX Loss of Lock Alarm"
::= { xfp1Entry 14 }

xfp1LasFault OBJECT-TYPE
	SYNTAX OCTET STRING 
	MAX-ACCESS read-only
	STATUS current
	DESCRIPTION "XFP1 Laser Fault Alarm"
::= { xfp1Entry 15 }

xfp1Group OBJECT-GROUP
    OBJECTS { xfp1Pres, xfp1Loss, xfp1Rdy, xfp1Int, xfp1TxPow, xfp1RxPow, xfp1Temp, xfp1LowTxPow, xfp1HighTxPow, xfp1LowRxPow, xfp1HighRxPow, xfp1RxCdrLol, xfp1TxCdrLol, xfp1LasFault }
    STATUS  current
    DESCRIPTION
        "The xfp1Group group groups objects of xfp1."
    ::= { mxpConfigMIBGroups 3 }



xfp2Table OBJECT-TYPE
	SYNTAX	SEQUENCE OF Xfp2Entry
	MAX-ACCESS	not-accessible
	STATUS	current
	DESCRIPTION "A table containing information on xfp2."
::= { mxpConfigMIBObjects 4 }

xfp2Entry OBJECT-TYPE
	SYNTAX Xfp2Entry
	MAX-ACCESS not-accessible
	STATUS current
	DESCRIPTION "An entry of the xfp2 table."
	INDEX	{ xfp2Index }
::= { xfp2Table 1 }

Xfp2Entry ::= SEQUENCE { xfp2Index OCTET STRING, xfp2Pres OCTET STRING, xfp2Loss OCTET STRING, xfp2Rdy OCTET STRING, xfp2Int OCTET STRING, xfp2TxPow OCTET STRING, xfp2RxPow OCTET STRING, xfp2Temp OCTET STRING, xfp2LowTxPow OCTET STRING, xfp2HighTxPow OCTET STRING, xfp2LowRxPow OCTET STRING, xfp2HighRxPow OCTET STRING, xfp2RxCdrLol OCTET STRING, xfp2TxCdrLol OCTET STRING, xfp2LasFault OCTET STRING }

xfp2Index OBJECT-TYPE
	SYNTAX OCTET STRING (SIZE(1..32))
	MAX-ACCESS not-accessible
	STATUS current
	DESCRIPTION "Reference Index for each observed process."
::= { xfp2Entry 1 }

xfp2Pres OBJECT-TYPE
	SYNTAX OCTET STRING
	MAX-ACCESS read-only
	STATUS current
	DESCRIPTION "XFP2 Presence"
::= { xfp2Entry 2 }

xfp2Loss OBJECT-TYPE
	SYNTAX OCTET STRING 
	MAX-ACCESS read-only
	STATUS current
	DESCRIPTION "XFP2 Loss of Signal Indicator"
::= { xfp2Entry 3 }

xfp2Rdy OBJECT-TYPE
	SYNTAX OCTET STRING 
	MAX-ACCESS read-only
	STATUS current
	DESCRIPTION "XFP2 Ready"
::= { xfp2Entry 4 }

xfp2Int OBJECT-TYPE
	SYNTAX OCTET STRING 
	MAX-ACCESS read-only
	STATUS current
	DESCRIPTION "XFP2 Interruption signal"
::= { xfp2Entry 5 }

xfp2TxPow OBJECT-TYPE
	SYNTAX OCTET STRING 
	MAX-ACCESS read-only
	STATUS current
	DESCRIPTION "XFP2 TX Power"
::= { xfp2Entry 6 }

xfp2RxPow OBJECT-TYPE
	SYNTAX OCTET STRING 
	MAX-ACCESS read-only
	STATUS current
	DESCRIPTION "XFP2 RX Power"
::= { xfp2Entry 7 }

xfp2Temp OBJECT-TYPE
	SYNTAX OCTET STRING 
	MAX-ACCESS read-only
	STATUS current
	DESCRIPTION "XFP2Temperature"
::= { xfp2Entry 8 }

xfp2LowTxPow OBJECT-TYPE
	SYNTAX OCTET STRING 
	MAX-ACCESS read-only
	STATUS current
	DESCRIPTION "XFP2 Low TX Power Alarm"
::= { xfp2Entry 9 }

xfp2HighTxPow OBJECT-TYPE
	SYNTAX OCTET STRING 
	MAX-ACCESS read-only
	STATUS current
	DESCRIPTION "XFP2 High TX Power Alarm"
::= { xfp2Entry 10 }

xfp2LowRxPow OBJECT-TYPE
	SYNTAX OCTET STRING 
	MAX-ACCESS read-only
	STATUS current
	DESCRIPTION "XFP2 High RX Power Alarm"
::= { xfp2Entry 11 }

xfp2HighRxPow OBJECT-TYPE
	SYNTAX OCTET STRING 
	MAX-ACCESS read-only
	STATUS current
	DESCRIPTION "XFP2 High RX Power Alarm"
::= { xfp2Entry 12 }

xfp2RxCdrLol OBJECT-TYPE
	SYNTAX OCTET STRING 
	MAX-ACCESS read-only
	STATUS current
	DESCRIPTION "XFP2 RX Loss of Lock Alarm"
::= { xfp2Entry 13 }

xfp2TxCdrLol OBJECT-TYPE
	SYNTAX OCTET STRING 
	MAX-ACCESS read-only
	STATUS current
	DESCRIPTION "XFP2 TX Loss of Lock Alarm"
::= { xfp2Entry 14 }

xfp2LasFault OBJECT-TYPE
	SYNTAX OCTET STRING 
	MAX-ACCESS read-only
	STATUS current
	DESCRIPTION "XFP2 Laser Fault Alarm"
::= { xfp2Entry 15 }

xfp2Group OBJECT-GROUP
    OBJECTS { xfp2Pres, xfp2Loss, xfp2Rdy, xfp2Int, xfp2TxPow, xfp2RxPow, xfp2Temp, xfp2LowTxPow, xfp2HighTxPow, xfp2LowRxPow, xfp2HighRxPow, xfp2RxCdrLol, xfp2TxCdrLol, xfp2LasFault }
    STATUS  current
    DESCRIPTION
        "The xfp2Group group groups objects of xfp2."
    ::= { mxpConfigMIBGroups 4 }



xfp3Table OBJECT-TYPE
	SYNTAX	SEQUENCE OF Xfp3Entry
	MAX-ACCESS	not-accessible
	STATUS	current
	DESCRIPTION "A table containing information on xfp3."
::= { mxpConfigMIBObjects 5 }

xfp3Entry OBJECT-TYPE
	SYNTAX Xfp3Entry
	MAX-ACCESS not-accessible
	STATUS current
	DESCRIPTION "An entry of the xfp3 table."
	INDEX	{ xfp3Index }
::= { xfp3Table 1 }

Xfp3Entry ::= SEQUENCE { xfp3Index OCTET STRING, xfp3Pres OCTET STRING, xfp3Loss OCTET STRING, xfp3Rdy OCTET STRING, xfp3Int OCTET STRING, xfp3TxPow OCTET STRING, xfp3RxPow OCTET STRING, xfp3Temp OCTET STRING, xfp3LowTxPow OCTET STRING, xfp3HighTxPow OCTET STRING, xfp3LowRxPow OCTET STRING, xfp3HighRxPow OCTET STRING, xfp3RxCdrLol OCTET STRING, xfp3TxCdrLol OCTET STRING, xfp3LasFault OCTET STRING }

xfp3Index OBJECT-TYPE
	SYNTAX OCTET STRING (SIZE(1..32))
	MAX-ACCESS not-accessible
	STATUS current
	DESCRIPTION "Reference Index for each observed process."
::= { xfp3Entry 1 }

xfp3Pres OBJECT-TYPE
	SYNTAX OCTET STRING
	MAX-ACCESS read-only
	STATUS current
	DESCRIPTION "XFP3 Presence"
::= { xfp3Entry 2 }

xfp3Loss OBJECT-TYPE
	SYNTAX OCTET STRING 
	MAX-ACCESS read-only
	STATUS current
	DESCRIPTION "XFP3 Loss of Signal Indicator"
::= { xfp3Entry 3 }

xfp3Rdy OBJECT-TYPE
	SYNTAX OCTET STRING 
	MAX-ACCESS read-only
	STATUS current
	DESCRIPTION "XFP3 Ready"
::= { xfp3Entry 4 }

xfp3Int OBJECT-TYPE
	SYNTAX OCTET STRING 
	MAX-ACCESS read-only
	STATUS current
	DESCRIPTION "XFP3 Interruption signal"
::= { xfp3Entry 5 }

xfp3TxPow OBJECT-TYPE
	SYNTAX OCTET STRING 
	MAX-ACCESS read-only
	STATUS current
	DESCRIPTION "XFP3 TX Power"
::= { xfp3Entry 6 }

xfp3RxPow OBJECT-TYPE
	SYNTAX OCTET STRING 
	MAX-ACCESS read-only
	STATUS current
	DESCRIPTION "XFP3 RX Power"
::= { xfp3Entry 7 }

xfp3Temp OBJECT-TYPE
	SYNTAX OCTET STRING 
	MAX-ACCESS read-only
	STATUS current
	DESCRIPTION "XFP3 Temperature"
::= { xfp3Entry 8 }

xfp3LowTxPow OBJECT-TYPE
	SYNTAX OCTET STRING 
	MAX-ACCESS read-only
	STATUS current
	DESCRIPTION "XFP3 Low TX Power Alarm"
::= { xfp3Entry 9 }

xfp3HighTxPow OBJECT-TYPE
	SYNTAX OCTET STRING 
	MAX-ACCESS read-only
	STATUS current
	DESCRIPTION "XFP3 High TX Power Alarm"
::= { xfp3Entry 10 }

xfp3LowRxPow OBJECT-TYPE
	SYNTAX OCTET STRING 
	MAX-ACCESS read-only
	STATUS current
	DESCRIPTION "XFP3 High RX Power Alarm"
::= { xfp3Entry 11 }

xfp3HighRxPow OBJECT-TYPE
	SYNTAX OCTET STRING 
	MAX-ACCESS read-only
	STATUS current
	DESCRIPTION "XFP3 High RX Power Alarm"
::= { xfp3Entry 12 }

xfp3RxCdrLol OBJECT-TYPE
	SYNTAX OCTET STRING 
	MAX-ACCESS read-only
	STATUS current
	DESCRIPTION "XFP3 RX Loss of Lock Alarm"
::= { xfp3Entry 13 }

xfp3TxCdrLol OBJECT-TYPE
	SYNTAX OCTET STRING 
	MAX-ACCESS read-only
	STATUS current
	DESCRIPTION "XFP3 TX Loss of Lock Alarm"
::= { xfp3Entry 14 }

xfp3LasFault OBJECT-TYPE
	SYNTAX OCTET STRING 
	MAX-ACCESS read-only
	STATUS current
	DESCRIPTION "XFP3 Laser Fault Alarm"
::= { xfp3Entry 15 }

xfp3Group OBJECT-GROUP
    OBJECTS { xfp3Pres, xfp3Loss, xfp3Rdy, xfp3Int, xfp3TxPow, xfp3RxPow, xfp3Temp, xfp3LowTxPow, xfp3HighTxPow, xfp3LowRxPow, xfp3HighRxPow, xfp3RxCdrLol, xfp3TxCdrLol, xfp3LasFault }
    STATUS  current
    DESCRIPTION
        "The xfp3Group group groups objects of xfp3."
    ::= { mxpConfigMIBGroups 5 }



xfp4Table OBJECT-TYPE
	SYNTAX	SEQUENCE OF Xfp4Entry
	MAX-ACCESS	not-accessible
	STATUS	current
	DESCRIPTION "A table containing information on xfp4."
::= { mxpConfigMIBObjects 6 }

xfp4Entry OBJECT-TYPE
	SYNTAX Xfp4Entry
	MAX-ACCESS not-accessible
	STATUS current
	DESCRIPTION "An entry of the xfp4 table."
	INDEX	{ xfp4Index }
::= { xfp4Table 1 }

Xfp4Entry ::= SEQUENCE { xfp4Index OCTET STRING, xfp4Pres OCTET STRING, xfp4Loss OCTET STRING, xfp4Rdy OCTET STRING, xfp4Int OCTET STRING, xfp4TxPow OCTET STRING, xfp4RxPow OCTET STRING, xfp4Temp OCTET STRING, xfp4LowTxPow OCTET STRING, xfp4HighTxPow OCTET STRING, xfp4LowRxPow OCTET STRING, xfp4HighRxPow OCTET STRING, xfp4RxCdrLol OCTET STRING, xfp4TxCdrLol OCTET STRING, xfp4LasFault OCTET STRING }

xfp4Index OBJECT-TYPE
	SYNTAX OCTET STRING (SIZE(1..32))
	MAX-ACCESS not-accessible
	STATUS current
	DESCRIPTION "Reference Index for each observed process."
::= { xfp4Entry 1 }

xfp4Pres OBJECT-TYPE
	SYNTAX OCTET STRING
	MAX-ACCESS read-only
	STATUS current
	DESCRIPTION "XFP4 Presence"
::= { xfp4Entry 2 }

xfp4Loss OBJECT-TYPE
	SYNTAX OCTET STRING 
	MAX-ACCESS read-only
	STATUS current
	DESCRIPTION "XFP4 Loss of Signal Indicator"
::= { xfp4Entry 3 }

xfp4Rdy OBJECT-TYPE
	SYNTAX OCTET STRING 
	MAX-ACCESS read-only
	STATUS current
	DESCRIPTION "XFP4 Ready"
::= { xfp4Entry 4 }

xfp4Int OBJECT-TYPE
	SYNTAX OCTET STRING 
	MAX-ACCESS read-only
	STATUS current
	DESCRIPTION "XFP4 Interruption signal"
::= { xfp4Entry 5 }

xfp4TxPow OBJECT-TYPE
	SYNTAX OCTET STRING 
	MAX-ACCESS read-only
	STATUS current
	DESCRIPTION "XFP4 TX Power"
::= { xfp4Entry 6 }

xfp4RxPow OBJECT-TYPE
	SYNTAX OCTET STRING 
	MAX-ACCESS read-only
	STATUS current
	DESCRIPTION "XFP4 RX Power"
::= { xfp4Entry 7 }

xfp4Temp OBJECT-TYPE
	SYNTAX OCTET STRING 
	MAX-ACCESS read-only
	STATUS current
	DESCRIPTION "XFP4 Temperature"
::= { xfp4Entry 8 }

xfp4LowTxPow OBJECT-TYPE
	SYNTAX OCTET STRING 
	MAX-ACCESS read-only
	STATUS current
	DESCRIPTION "XFP4 Low TX Power Alarm"
::= { xfp4Entry 9 }

xfp4HighTxPow OBJECT-TYPE
	SYNTAX OCTET STRING 
	MAX-ACCESS read-only
	STATUS current
	DESCRIPTION "XFP4 High TX Power Alarm"
::= { xfp4Entry 10 }

xfp4LowRxPow OBJECT-TYPE
	SYNTAX OCTET STRING 
	MAX-ACCESS read-only
	STATUS current
	DESCRIPTION "XFP4 High RX Power Alarm"
::= { xfp4Entry 11 }

xfp4HighRxPow OBJECT-TYPE
	SYNTAX OCTET STRING 
	MAX-ACCESS read-only
	STATUS current
	DESCRIPTION "XFP4 High RX Power Alarm"
::= { xfp4Entry 12 }

xfp4RxCdrLol OBJECT-TYPE
	SYNTAX OCTET STRING 
	MAX-ACCESS read-only
	STATUS current
	DESCRIPTION "XFP4 RX Loss of Lock Alarm"
::= { xfp4Entry 13 }

xfp4TxCdrLol OBJECT-TYPE
	SYNTAX OCTET STRING 
	MAX-ACCESS read-only
	STATUS current
	DESCRIPTION "XFP4 TX Loss of Lock Alarm"
::= { xfp4Entry 14 }

xfp4LasFault OBJECT-TYPE
	SYNTAX OCTET STRING 
	MAX-ACCESS read-only
	STATUS current
	DESCRIPTION "XFP4 Laser Fault Alarm"
::= { xfp4Entry 15 }

xfp4Group OBJECT-GROUP
    OBJECTS { xfp4Pres, xfp4Loss, xfp4Rdy, xfp4Int, xfp4TxPow, xfp4RxPow, xfp4Temp, xfp4LowTxPow, xfp4HighTxPow, xfp4LowRxPow, xfp4HighRxPow, xfp4RxCdrLol, xfp4TxCdrLol, xfp4LasFault }
    STATUS  current
    DESCRIPTION
        "The xfp4Group group groups objects of xfp4."
    ::= { mxpConfigMIBGroups 6 }



mxpEnvTable OBJECT-TYPE
	SYNTAX SEQUENCE OF MxpEnvEntry
	MAX-ACCESS not-accessible
	STATUS current
	DESCRIPTION "A table containing information on Environment."
::= { mxpConfigMIBObjects 7 }

mxpEnvEntry OBJECT-TYPE
	SYNTAX MxpEnvEntry
	MAX-ACCESS not-accessible
	STATUS current
	DESCRIPTION "An entry of the environment table."
	INDEX { mxpEnvIndex }
::= { mxpEnvTable  1 }

MxpEnvEntry ::= SEQUENCE { mxpEnvIndex OCTET STRING, mxpTempT41Around OCTET STRING, mxpTempT41TS0 OCTET STRING, mxpTempT41TS1 OCTET STRING, mxpTempT41TS2 OCTET STRING, mxpTempFPGA OCTET STRING, mxpTempBOARD OCTET STRING, mxpTempEdfa OCTET STRING, mxpHumedity OCTET STRING }

mxpEnvIndex OBJECT-TYPE
	SYNTAX OCTET STRING (SIZE(1..32))
	MAX-ACCESS not-accessible
	STATUS current
	DESCRIPTION "Reference Index for each observed process."
::= { mxpEnvEntry 1 }

mxpTempT41Around OBJECT-TYPE
	SYNTAX OCTET STRING 
	MAX-ACCESS read-only
	STATUS current
	DESCRIPTION "Temperature around cs6041"
::= { mxpEnvEntry 2 }

mxpTempT41TS0 OBJECT-TYPE
	SYNTAX OCTET STRING 
	MAX-ACCESS read-only
	STATUS current
	DESCRIPTION "Temperature cs6041 TS0"
::= { mxpEnvEntry 3 }

mxpTempT41TS1 OBJECT-TYPE
	SYNTAX OCTET STRING 
	MAX-ACCESS read-only
	STATUS current
	DESCRIPTION "Temperature cs6041 TS1"
::= { mxpEnvEntry 4 }

mxpTempT41TS2 OBJECT-TYPE
	SYNTAX OCTET STRING 
	MAX-ACCESS read-only
	STATUS current
	DESCRIPTION "Temperature cs6041 TS2"
::= { mxpEnvEntry 5 }

mxpTempFPGA OBJECT-TYPE
	SYNTAX OCTET STRING 
	MAX-ACCESS read-only
	STATUS current
	DESCRIPTION "Temperature FPGA"
::= { mxpEnvEntry 6 }

mxpTempBOARD OBJECT-TYPE
	SYNTAX OCTET STRING
	MAX-ACCESS read-only
	STATUS current
	DESCRIPTION "Temperature BOARD"
::= { mxpEnvEntry 7 }

mxpTempEdfa OBJECT-TYPE
	SYNTAX      OCTET STRING 
	MAX-ACCESS  read-only
	STATUS      current
	DESCRIPTION "Temperature edfa"
::= { mxpEnvEntry 8 }

mxpHumedity OBJECT-TYPE
	SYNTAX OCTET STRING 
	MAX-ACCESS read-only
	STATUS current
	DESCRIPTION "Muxponder humidity."
::= { mxpEnvEntry 9 }

envGroup OBJECT-GROUP
    OBJECTS { mxpTempT41Around, mxpTempT41TS0, mxpTempT41TS1, mxpTempT41TS2, mxpTempFPGA, mxpTempBOARD, mxpTempEdfa, mxpHumedity }
    STATUS  current
    DESCRIPTION
        "The envGroup group groups objects environment."
    ::= { mxpConfigMIBGroups 7 }



edfaTable OBJECT-TYPE
	SYNTAX SEQUENCE OF EdfaEntry
	MAX-ACCESS not-accessible
	STATUS current
	DESCRIPTION "A table containing information on EDFA."
::= { mxpConfigMIBObjects 8 }

edfaEntry OBJECT-TYPE
	SYNTAX EdfaEntry
	MAX-ACCESS not-accessible
	STATUS current
	DESCRIPTION "An entry of the EDFA table."
	INDEX { edfaIndex }
::= { edfaTable  1 }

EdfaEntry ::= SEQUENCE { edfaIndex OCTET STRING, edfaPout OCTET STRING, edfaPin OCTET STRING, edfaLos OCTET STRING, edfaLop OCTET STRING, edfaAmpStat OCTET STRING }

edfaIndex OBJECT-TYPE
	SYNTAX OCTET STRING (SIZE(1..32))
	MAX-ACCESS not-accessible
	STATUS current
	DESCRIPTION "Reference Index for each observed process."
::= { edfaEntry 1 }

edfaPout OBJECT-TYPE
	SYNTAX OCTET STRING 
	MAX-ACCESS read-only
	STATUS current
	DESCRIPTION "edfa output power"
::= { edfaEntry 2 }

edfaPin OBJECT-TYPE
	SYNTAX OCTET STRING 
	MAX-ACCESS read-only
	STATUS current
	DESCRIPTION "edfa input power"
::= { edfaEntry 3 }

edfaLos OBJECT-TYPE
	SYNTAX OCTET STRING 
	MAX-ACCESS read-only
	STATUS current
	DESCRIPTION "edfa loss of input power alarm"
::= { edfaEntry 4 }

edfaLop OBJECT-TYPE
	SYNTAX OCTET STRING 
	MAX-ACCESS read-only
	STATUS current
	DESCRIPTION "edfa loss of output power/gain alarm"
::= { edfaEntry 5 }

edfaAmpStat OBJECT-TYPE
	SYNTAX OCTET STRING 
	MAX-ACCESS read-only
	STATUS current
	DESCRIPTION "EDAF amplifier status"
::= { edfaEntry 6 }

edfaGroup OBJECT-GROUP
    OBJECTS { edfaPout, edfaPin, edfaLos, edfaLop, edfaAmpStat }
    STATUS  current
    DESCRIPTION
        "The edfaGroup group groups objects of edfa."
    ::= { mxpConfigMIBGroups 8 }



txp OBJECT IDENTIFIER ::= { mxpConfigMIBObjects 9 }

txpAlrm OBJECT IDENTIFIER ::= { txp 1 }

txpAlrmTxTable OBJECT-TYPE
	SYNTAX SEQUENCE OF TxpAlrmTxEntry
	MAX-ACCESS not-accessible
	STATUS current
	DESCRIPTION "A table containing information on Alarm TX of TXP."
::= { txpAlrm 1 }

txpAlrmTxEntry OBJECT-TYPE
	SYNTAX TxpAlrmTxEntry
	MAX-ACCESS not-accessible
	STATUS current
	DESCRIPTION "An entry of the TXP Alarm table."
	INDEX { txpAlrmTxIndex }
::= { txpAlrmTxTable  1 }

TxpAlrmTxEntry ::= SEQUENCE { txpAlrmTxIndex OCTET STRING, txpEOLALM OCTET STRING, txpModTEMPALM OCTET STRING, txpTxOOA OCTET STRING, txpTxLOFALM OCTET STRING, txpTxDSCERR OCTET STRING, txpLsWAVALM OCTET STRING, txpTxALMINT OCTET STRING, txpLsBIASALM OCTET STRING, txpLsTEMPALM OCTET STRING, txpTxLOCKERR OCTET STRING, txpLsPOWALM OCTET STRING, txpModBIASALM OCTET STRING, txpLATCHEDTxFIFOERR OCTET STRING }

txpAlrmTxIndex OBJECT-TYPE
	SYNTAX OCTET STRING (SIZE(1..32))
	MAX-ACCESS not-accessible
	STATUS current
	DESCRIPTION "Reference Index for each observed process."
::= { txpAlrmTxEntry 1 }

txpEOLALM OBJECT-TYPE
	SYNTAX OCTET STRING 
	MAX-ACCESS read-only
	STATUS current
	DESCRIPTION "Line transmiter laser end of life alarm."
::= { txpAlrmTxEntry 2 }

txpModTEMPALM OBJECT-TYPE
	SYNTAX OCTET STRING 
	MAX-ACCESS read-only
	STATUS current
	DESCRIPTION "Line transmiter modulator Temperature Alarm."
::= { txpAlrmTxEntry 3 }

txpTxOOA OBJECT-TYPE
	SYNTAX OCTET STRING 
	MAX-ACCESS read-only
	STATUS current
	DESCRIPTION "Line transmiter SFI-5 Deskew alarm"
::= { txpAlrmTxEntry 4 }

txpTxLOFALM OBJECT-TYPE
	SYNTAX OCTET STRING 
	MAX-ACCESS read-only
	STATUS current
	DESCRIPTION "Line transmiter loss of Frame alarm."
::= { txpAlrmTxEntry 5 }

txpTxDSCERR OBJECT-TYPE
	SYNTAX OCTET STRING 
	MAX-ACCESS read-only
	STATUS current
	DESCRIPTION "Line transmiter latching SFI-5 DESKEW Channel error."
::= { txpAlrmTxEntry 6 }

txpLsWAVALM OBJECT-TYPE
	SYNTAX OCTET STRING 
	MAX-ACCESS read-only
	STATUS current
	DESCRIPTION "Line transmiter laser Wavelength Alarm."
::= { txpAlrmTxEntry 7 }

txpTxALMINT OBJECT-TYPE
	SYNTAX OCTET STRING 
	MAX-ACCESS read-only
	STATUS current
	DESCRIPTION "Line transmiter Tx summary alarm."
::= { txpAlrmTxEntry 8 }

txpLsBIASALM OBJECT-TYPE
	SYNTAX OCTET STRING 
	MAX-ACCESS read-only
	STATUS current
	DESCRIPTION "Line transmiter laser bias current alarm."
::= { txpAlrmTxEntry 9 }

txpLsTEMPALM OBJECT-TYPE
	SYNTAX OCTET STRING 
	MAX-ACCESS read-only
	STATUS current
	DESCRIPTION "Line transmiter laser Temperature alarm."
::= { txpAlrmTxEntry 10 }

txpTxLOCKERR OBJECT-TYPE
	SYNTAX OCTET STRING 
	MAX-ACCESS read-only
	STATUS current
	DESCRIPTION "Line transmiter loss of TxPLL lock indicator."
::= { txpAlrmTxEntry 11 }

txpLsPOWALM OBJECT-TYPE
	SYNTAX OCTET STRING 
	MAX-ACCESS read-only
	STATUS current
	DESCRIPTION "Line transmiter laser power alarm."
::= { txpAlrmTxEntry 12 }

txpModBIASALM OBJECT-TYPE
	SYNTAX OCTET STRING 
	MAX-ACCESS  read-only
	STATUS      current
	DESCRIPTION "Line transmiter modulator bias alarm."
::= { txpAlrmTxEntry 13 }

txpLATCHEDTxFIFOERR OBJECT-TYPE
	SYNTAX OCTET STRING 
	MAX-ACCESS read-only
	STATUS current
	DESCRIPTION "Line transmiter historical Mux FIFO error indicator."
::= { txpAlrmTxEntry 14 }

txpAlrmTxGroup OBJECT-GROUP
    OBJECTS { txpEOLALM, txpModTEMPALM, txpTxOOA, txpTxLOFALM, txpTxDSCERR, txpLsWAVALM, txpTxALMINT, txpLsBIASALM, txpLsTEMPALM, txpTxLOCKERR, txpLsPOWALM, txpModBIASALM, txpLATCHEDTxFIFOERR }
    STATUS  current
    DESCRIPTION
        "The txpAlrmTxGroup group groups objects of TXP Alarm Tx."
    ::= { mxpConfigMIBGroups 9 }



txpAlrmRxTable OBJECT-TYPE
	SYNTAX SEQUENCE OF TxpAlrmRxEntry
	MAX-ACCESS not-accessible
	STATUS current
	DESCRIPTION "A table containing information on Alarm RX of TXP."
::= { txpAlrm 2 }

txpAlrmRxEntry OBJECT-TYPE
	SYNTAX TxpAlrmRxEntry
	MAX-ACCESS not-accessible
	STATUS current
	DESCRIPTION "An entry of the TXP Alarm table."
	INDEX { txpAlrmRxIndex }
::= { txpAlrmRxTable 1 }

TxpAlrmRxEntry ::= SEQUENCE { txpAlrmRxIndex OCTET STRING, txpRxALMINT OCTET STRING, txpRxPOWALM OCTET STRING, txpRxLOS OCTET STRING, txpRxLOCKERR OCTET STRING, txpRXS OCTET STRING, txpPRBSERRDET OCTET STRING }

txpAlrmRxIndex OBJECT-TYPE
	SYNTAX OCTET STRING (SIZE(1..32))
	MAX-ACCESS not-accessible
	STATUS current
	DESCRIPTION "Reference Index for each observed process."
::= { txpAlrmRxEntry 1 }

txpRxALMINT OBJECT-TYPE
	SYNTAX OCTET STRING 
	MAX-ACCESS read-only
	STATUS current
	DESCRIPTION "Line receiver Rx summary alarm."
::= { txpAlrmRxEntry 2 }

txpRxPOWALM OBJECT-TYPE
	SYNTAX OCTET STRING 
	MAX-ACCESS read-only
	STATUS current
	DESCRIPTION "Line receiver loss average optical power alarm."
::= { txpAlrmRxEntry 3 }

txpRxLOS OBJECT-TYPE
	SYNTAX OCTET STRING 
	MAX-ACCESS read-only
	STATUS current
	DESCRIPTION "Line receiver loss AC (modulated) power alarm."
::= { txpAlrmRxEntry 4 }

txpRxLOCKERR OBJECT-TYPE
	SYNTAX OCTET STRING 
	MAX-ACCESS read-only
	STATUS current
	DESCRIPTION "Line receiver loss of RxPLL lock indicator."
::= { txpAlrmRxEntry 5 }

txpRXS OBJECT-TYPE
	SYNTAX OCTET STRING 
	MAX-ACCESS read-only
	STATUS current
	DESCRIPTION "Line receiver SFI-5 DEMUX status."
::= { txpAlrmRxEntry 6 }

txpPRBSERRDET OBJECT-TYPE
	SYNTAX OCTET STRING 
	MAX-ACCESS read-only
	STATUS current
	DESCRIPTION "Line receiver PRBSERRDET (an error was detected by the PRBS error checker)."
::= { txpAlrmRxEntry 7 }

txpAlrmRxGroup OBJECT-GROUP
    OBJECTS { txpRxALMINT, txpRxPOWALM, txpRxLOS, txpRxLOCKERR, txpRXS, txpPRBSERRDET }
    STATUS  current
    DESCRIPTION
        "The txpAlrmRxGroup group groups objects of TXP Alarm Rx."
    ::= { mxpConfigMIBGroups 10 }



txpPowSupplyAlrmTable OBJECT-TYPE
	SYNTAX SEQUENCE OF TxpPowSupplyAlrmEntry
	MAX-ACCESS not-accessible
	STATUS current
	DESCRIPTION "A table containing information on Power Supply Alarm of TXP."
::= { txpAlrm 3 }

txpPowSupplyAlrmEntry OBJECT-TYPE
	SYNTAX TxpPowSupplyAlrmEntry
	MAX-ACCESS not-accessible
	STATUS current
	DESCRIPTION "An entry of the TXP Alarm table."
	INDEX { txpPowSupplyAlrmIndex }
::= { txpPowSupplyAlrmTable 1 }

TxpPowSupplyAlrmEntry ::= SEQUENCE { txpPowSupplyAlrmIndex OCTET STRING, txpPSUMMARY OCTET STRING, txpP5VANALOG OCTET STRING, txpN5V2ANALOG OCTET STRING, txpP3P3VANALOG OCTET STRING, txpP3P3VDIGITAL OCTET STRING, txpLVDIGITAL OCTET STRING, txpN5P2VDIGITAL OCTET STRING }

txpPowSupplyAlrmIndex OBJECT-TYPE
	SYNTAX OCTET STRING (SIZE(1..32))
	MAX-ACCESS not-accessible
	STATUS current
	DESCRIPTION "Reference Index for each observed process."
::= { txpPowSupplyAlrmEntry 1 }

txpPSUMMARY OBJECT-TYPE
	SYNTAX OCTET STRING 
	MAX-ACCESS read-only
	STATUS current
	DESCRIPTION "txp40G Power summary alarm."
::= { txpPowSupplyAlrmEntry 2 }

txpP5VANALOG OBJECT-TYPE
	SYNTAX OCTET STRING 
	MAX-ACCESS read-only
	STATUS current
	DESCRIPTION "txp40G +5V analog alarm."
::= { txpPowSupplyAlrmEntry 3 }

txpN5V2ANALOG OBJECT-TYPE
	SYNTAX OCTET STRING 
	MAX-ACCESS read-only
	STATUS current
	DESCRIPTION "txp40G -5,2V analog alarm."
::= { txpPowSupplyAlrmEntry 4 }

txpP3P3VANALOG OBJECT-TYPE
	SYNTAX OCTET STRING 
	MAX-ACCESS read-only
	STATUS current
	DESCRIPTION "Txp40G +3,3V analog alarm."
::= { txpPowSupplyAlrmEntry 5 }

txpP3P3VDIGITAL OBJECT-TYPE
	SYNTAX OCTET STRING 
	MAX-ACCESS read-only
	STATUS current
	DESCRIPTION "Txp40G +3,3V analog alarm."
::= { txpPowSupplyAlrmEntry 6 }

txpLVDIGITAL OBJECT-TYPE
	SYNTAX OCTET STRING 
	MAX-ACCESS read-only
	STATUS current
	DESCRIPTION "txp40G low voltage digital."
::= { txpPowSupplyAlrmEntry 7 }

txpN5P2VDIGITAL OBJECT-TYPE
	SYNTAX OCTET STRING 
	MAX-ACCESS read-only
	STATUS current
	DESCRIPTION "txp40G -5,2V digital alarm."
::= { txpPowSupplyAlrmEntry 8 }

txpPowSupplyAlrmGroup OBJECT-GROUP
    OBJECTS { txpPSUMMARY, txpP5VANALOG, txpN5V2ANALOG, txpP3P3VANALOG, txpP3P3VDIGITAL, txpLVDIGITAL, txpN5P2VDIGITAL }
    STATUS  current
    DESCRIPTION
        "The txpPowSupplyAlrmGroup group groups objects of TXP Power Supply Alrm."
    ::= { mxpConfigMIBGroups 11 }



txpMiscellaneous OBJECT IDENTIFIER ::= { txp 2 }

txpTempTable OBJECT-TYPE
	SYNTAX SEQUENCE OF TxpTempEntry
	MAX-ACCESS not-accessible
	STATUS current
	DESCRIPTION "A table containing information on Temperature TXP."
::= { txpMiscellaneous 1 }

txpTempEntry OBJECT-TYPE
	SYNTAX TxpTempEntry
	MAX-ACCESS not-accessible
	STATUS current
	DESCRIPTION "An entry of the Temperature TXP."
	INDEX { txpTempIndex }
::= { txpTempTable  1 }

TxpTempEntry ::= SEQUENCE { txpTempIndex OCTET STRING, txpTempAround OCTET STRING, txpTempCase OCTET STRING, txpTempTxLaser OCTET STRING, txpTempRxLaser OCTET STRING }

txpTempIndex OBJECT-TYPE
	SYNTAX OCTET STRING (SIZE(1..32))
	MAX-ACCESS not-accessible
	STATUS current
	DESCRIPTION "Reference Index for each observed process."
::= { txpTempEntry 1 }

txpTempAround OBJECT-TYPE
	SYNTAX      OCTET STRING 
	MAX-ACCESS  read-only
	STATUS      current
	DESCRIPTION "Temperature around txp40G."
::= { txpTempEntry 2 }

txpTempCase OBJECT-TYPE
	SYNTAX      OCTET STRING 
	MAX-ACCESS  read-only
	STATUS      current
	DESCRIPTION "Temperature case txp40G."
::= { txpTempEntry 3 }

txpTempTxLaser OBJECT-TYPE
	SYNTAX      OCTET STRING 
	MAX-ACCESS  read-only
	STATUS      current
	DESCRIPTION "Temperature Tx laser txp40G."
::= { txpTempEntry 4 }

txpTempRxLaser OBJECT-TYPE
	SYNTAX      OCTET STRING 
	MAX-ACCESS  read-only
	STATUS      current
	DESCRIPTION "Temperature Rx laser txp40G."
::= { txpTempEntry 5 }

txpTempGroup OBJECT-GROUP
    OBJECTS { txpTempAround, txpTempCase, txpTempTxLaser, txpTempRxLaser }
    STATUS  current
    DESCRIPTION
        "The txpTempGroup group groups objects of TXP Temperature Alrm."
    ::= { mxpConfigMIBGroups 12 }



txpPowerTable OBJECT-TYPE
	SYNTAX SEQUENCE OF TxpPowerEntry
	MAX-ACCESS not-accessible
	STATUS current
	DESCRIPTION "A table containing information on Power TXP."
::= { txpMiscellaneous 2 }

txpPowerEntry OBJECT-TYPE
	SYNTAX TxpPowerEntry
	MAX-ACCESS not-accessible
	STATUS current
	DESCRIPTION "An entry of the Power TXP."
	INDEX { txpPowerIndex }
::= { txpPowerTable  1 }

TxpPowerEntry ::= SEQUENCE { txpPowerIndex OCTET STRING, txpTxPower OCTET STRING, txpRxPower OCTET STRING }

txpPowerIndex OBJECT-TYPE
	SYNTAX OCTET STRING (SIZE(1..32))
	MAX-ACCESS not-accessible
	STATUS current
	DESCRIPTION "Reference Index for each observed process."
::= { txpPowerEntry 1 }

txpTxPower OBJECT-TYPE
	SYNTAX OCTET STRING 
	MAX-ACCESS read-only
	STATUS current
	DESCRIPTION "Line Tx power."
::= { txpPowerEntry 2 }

txpRxPower OBJECT-TYPE
	SYNTAX OCTET STRING 
	MAX-ACCESS read-only
	STATUS current
	DESCRIPTION "Line Rx power."
::= { txpPowerEntry 3 }

txpPowerGroup OBJECT-GROUP
    OBJECTS { txpTxPower, txpRxPower }
    STATUS  current
    DESCRIPTION
        "The txpPowerGroup group groups objects of TXP Power."
    ::= { mxpConfigMIBGroups 13 }



txpChannelTable OBJECT-TYPE
	SYNTAX SEQUENCE OF TxpChannelEntry
	MAX-ACCESS not-accessible
	STATUS current
	DESCRIPTION "A table containing information on Channel TXP."
::= { txpMiscellaneous 3 }

txpChannelEntry OBJECT-TYPE
	SYNTAX TxpChannelEntry
	MAX-ACCESS not-accessible
	STATUS current
	DESCRIPTION "An entry of the Channel TXP."
	INDEX { txpChannelIndex }
::= { txpChannelTable  1 }

TxpChannelEntry ::= SEQUENCE { txpChannelIndex OCTET STRING, txpTxLaserITUChannel OCTET STRING, txpRxLaserITUChannel OCTET STRING }

txpChannelIndex OBJECT-TYPE
	SYNTAX OCTET STRING (SIZE(1..32))
	MAX-ACCESS not-accessible
	STATUS current
	DESCRIPTION "Reference Index for each observed process."
::= { txpChannelEntry 1 }

txpTxLaserITUChannel OBJECT-TYPE
	SYNTAX OCTET STRING 
	MAX-ACCESS read-only
	STATUS current
	DESCRIPTION "txp40G Tx laser ITU Channel."
::= { txpChannelEntry 2 }

txpRxLaserITUChannel OBJECT-TYPE
	SYNTAX OCTET STRING 
	MAX-ACCESS read-only
	STATUS current
	DESCRIPTION "txp40G Rx laser ITU Channel."
::= { txpChannelEntry 3 }

txpChannelGroup OBJECT-GROUP
    OBJECTS { txpTxLaserITUChannel, txpRxLaserITUChannel }
    STATUS  current
    DESCRIPTION
        "The txpChannelGroup group groups objects of TXP Channel."
    ::= { mxpConfigMIBGroups 14 }



txpBandTable OBJECT-TYPE
	SYNTAX SEQUENCE OF TxpBandEntry
	MAX-ACCESS not-accessible
	STATUS current
	DESCRIPTION "A table containing information on Band TXP."
::= { txpMiscellaneous 4 }

txpBandEntry OBJECT-TYPE
	SYNTAX TxpBandEntry
	MAX-ACCESS not-accessible
	STATUS current
	DESCRIPTION "An entry of the Band TXP."
	INDEX { txpBandIndex }
::= { txpBandTable  1 }

TxpBandEntry ::= SEQUENCE { txpBandIndex OCTET STRING, txpTxLaserITUBand OCTET STRING, txpRxLaserITUBand OCTET STRING }

txpBandIndex OBJECT-TYPE
	SYNTAX OCTET STRING (SIZE(1..32))
	MAX-ACCESS not-accessible
	STATUS current
	DESCRIPTION "Reference Index for each observed process."
::= { txpBandEntry 1 }

txpTxLaserITUBand OBJECT-TYPE
	SYNTAX OCTET STRING 
	MAX-ACCESS read-only
	STATUS current
	DESCRIPTION "txp40G Tx laser ITU Band."
::= { txpBandEntry 2 }

txpRxLaserITUBand OBJECT-TYPE
	SYNTAX OCTET STRING 
	MAX-ACCESS read-only
	STATUS current
	DESCRIPTION "txp40G Rx laser ITU Band."
::= { txpBandEntry 3 }

txpBandGroup OBJECT-GROUP
    OBJECTS { txpTxLaserITUBand, txpRxLaserITUBand }
    STATUS  current
    DESCRIPTION
        "The txpBandGroup group groups objects of TXP Band."
    ::= { mxpConfigMIBGroups 15 }


txpPhyspadTable OBJECT-TYPE
	SYNTAX SEQUENCE OF TxpPhyspadEntry
	MAX-ACCESS not-accessible
	STATUS current
	DESCRIPTION "A table containing information on physical pad."
::= { txpMiscellaneous 5 }

txpPhyspadEntry OBJECT-TYPE
	SYNTAX TxpPhyspadEntry
	MAX-ACCESS not-accessible
	STATUS current
	DESCRIPTION "An entry of the physical pad."
	INDEX { txpPhyspadIndex }
::= { txpPhyspadTable  1 }

TxpPhyspadEntry ::= SEQUENCE { txpPhyspadIndex OCTET STRING, txpLoss OCTET STRING, txpInterrupt OCTET STRING }

txpPhyspadIndex OBJECT-TYPE
	SYNTAX OCTET STRING (SIZE(1..32))
	MAX-ACCESS not-accessible
	STATUS current
	DESCRIPTION "Reference Index for each observed process."
::= { txpPhyspadEntry 1 }

txpLoss OBJECT-TYPE
	SYNTAX OCTET STRING 
	MAX-ACCESS read-only
	STATUS current
	DESCRIPTION "txp40G pin loss input alarm."
::= { txpPhyspadEntry 2 }

txpInterrupt OBJECT-TYPE
	SYNTAX OCTET STRING 
	MAX-ACCESS read-only
	STATUS current
	DESCRIPTION "txp40G pin interrupt alarm."
::= { txpPhyspadEntry 3 }

txpPhyspadGroup OBJECT-GROUP
    OBJECTS { txpLoss, txpInterrupt }
    STATUS  current
    DESCRIPTION
        "The txpPhyspadGroup group groups objects of TXP Physical Pad."
    ::= { mxpConfigMIBGroups 16 }
    


txpDSP OBJECT IDENTIFIER ::= { txp 3 }

txpDSPStatusTable OBJECT-TYPE
	SYNTAX SEQUENCE OF TxpDSPStatusEntry
	MAX-ACCESS not-accessible
	STATUS current
	DESCRIPTION "A table containing information on TXP DSP Status."
::= { txpDSP 1 }

txpDSPStatusEntry OBJECT-TYPE
	SYNTAX TxpDSPStatusEntry
	MAX-ACCESS not-accessible
	STATUS current
	DESCRIPTION "An entry of the TXP DSP Status."
	INDEX { txpDSPStatusIndex }
::= { txpDSPStatusTable 1 }

TxpDSPStatusEntry ::= SEQUENCE { txpDSPStatusIndex OCTET STRING, dsprunning OCTET STRING, converged OCTET STRING, msebelowThreshold OCTET STRING, bcdEnable OCTET STRING, coarseCarrierLock OCTET STRING, collision OCTET STRING, dspInitialized OCTET STRING, presenceOfLight OCTET STRING, localOscillatorRunning OCTET STRING, transmitLaserRunning OCTET STRING }

txpDSPStatusIndex OBJECT-TYPE
	SYNTAX OCTET STRING (SIZE(1..32))
	MAX-ACCESS not-accessible
	STATUS current
	DESCRIPTION "Reference Index for each observed process."
::= { txpDSPStatusEntry 1 }

dsprunning OBJECT-TYPE
	SYNTAX OCTET STRING 
	MAX-ACCESS read-only
	STATUS current
	DESCRIPTION "txp40G DSP running."
::= { txpDSPStatusEntry 2 }

converged OBJECT-TYPE
	SYNTAX OCTET STRING 
	MAX-ACCESS read-only
	STATUS current
	DESCRIPTION "txp40G DSP Converged algorithms."
::= { txpDSPStatusEntry 3 }

msebelowThreshold OBJECT-TYPE
	SYNTAX OCTET STRING 
	MAX-ACCESS  read-only
	STATUS      current
	DESCRIPTION "txp40G DSP MSE below threshold"
::= { txpDSPStatusEntry 4 }

bcdEnable OBJECT-TYPE
	SYNTAX OCTET STRING 
	MAX-ACCESS read-only
	STATUS current
	DESCRIPTION "txp40G DSP enable."
::= { txpDSPStatusEntry 5 }

coarseCarrierLock OBJECT-TYPE
	SYNTAX OCTET STRING 
	MAX-ACCESS read-only
	STATUS current
	DESCRIPTION "txp40G DSP Coarse Carrier Lock."
::= { txpDSPStatusEntry 6 }

collision OBJECT-TYPE
	SYNTAX OCTET STRING 
	MAX-ACCESS read-only
	STATUS current
	DESCRIPTION "txp40G DSP Collision."
::= { txpDSPStatusEntry 7 }

dspInitialized OBJECT-TYPE
	SYNTAX OCTET STRING 
	MAX-ACCESS read-only
	STATUS current
	DESCRIPTION "txp40G DSP Initialized."
::= { txpDSPStatusEntry 8 }

presenceOfLight OBJECT-TYPE
	SYNTAX OCTET STRING 
	MAX-ACCESS read-only
	STATUS current
	DESCRIPTION "txp40G DSP Presence Of Light."
::= { txpDSPStatusEntry 9 }

localOscillatorRunning OBJECT-TYPE
	SYNTAX OCTET STRING 
	MAX-ACCESS read-only
	STATUS current
	DESCRIPTION "txp40G DSP Local oscillator running."
::= { txpDSPStatusEntry 10 }

transmitLaserRunning OBJECT-TYPE
	SYNTAX OCTET STRING 
	MAX-ACCESS read-only
	STATUS current
	DESCRIPTION "txp40G DSP Transmit laser running."
::= { txpDSPStatusEntry 11 }

txpDSPStatusGroup OBJECT-GROUP
    OBJECTS { dsprunning, converged, msebelowThreshold, bcdEnable, coarseCarrierLock, collision, dspInitialized, presenceOfLight, localOscillatorRunning, transmitLaserRunning }
    STATUS  current
    DESCRIPTION
        "The txpDSPStatusGroup group groups objects of TXP DSP Status."
    ::= { mxpConfigMIBGroups 17 }



txpDSPErrorsTable OBJECT-TYPE
	SYNTAX SEQUENCE OF TxpDSPErrorsEntry
	MAX-ACCESS not-accessible
	STATUS current
	DESCRIPTION "A table containing information on TXP DSP Error."
::= { txpDSP 2 }

txpDSPErrorsEntry OBJECT-TYPE
	SYNTAX TxpDSPErrorsEntry
	MAX-ACCESS not-accessible
	STATUS current
	DESCRIPTION "An entry of the TXP DSP Error."
	INDEX { txpDSPErrorsIndex }
::= { txpDSPErrorsTable 1 }

TxpDSPErrorsEntry ::= SEQUENCE { txpDSPErrorsIndex OCTET STRING, msexi OCTET STRING, msexq OCTET STRING, mseyi OCTET STRING, mseyq OCTET STRING, berestimate OCTET STRING }

txpDSPErrorsIndex OBJECT-TYPE
	SYNTAX OCTET STRING (SIZE(1..32))
	MAX-ACCESS not-accessible
	STATUS current
	DESCRIPTION "Reference Index for each observed process."
::= { txpDSPErrorsEntry 1 }

msexi OBJECT-TYPE
	SYNTAX OCTET STRING 
	MAX-ACCESS read-only
	STATUS current
	DESCRIPTION "txp40G DSP Mean Squared Error XI channel."
::= { txpDSPErrorsEntry 2 }

msexq OBJECT-TYPE
	SYNTAX OCTET STRING 
	MAX-ACCESS read-only
	STATUS current
	DESCRIPTION "txp40G DSP Mean Squared Error XQ channel."
::= { txpDSPErrorsEntry 3 }

mseyi OBJECT-TYPE
	SYNTAX OCTET STRING 
	MAX-ACCESS read-only
	STATUS current
	DESCRIPTION "txp40G DSP Mean Squared Error YI channel."
::= { txpDSPErrorsEntry 4 }

mseyq OBJECT-TYPE
	SYNTAX OCTET STRING 
	MAX-ACCESS read-only
	STATUS current
	DESCRIPTION "txp40G DSP Mean Squared Error YQ channel."
::= { txpDSPErrorsEntry 5 }

berestimate OBJECT-TYPE
	SYNTAX OCTET STRING 
	MAX-ACCESS read-only
	STATUS current
	DESCRIPTION "txp40G DSP BER Estimate."
::= { txpDSPErrorsEntry 6 }

txpDSPErrorsGroup OBJECT-GROUP
    OBJECTS { msexi, msexq, mseyi, mseyq, berestimate }
    STATUS  current
    DESCRIPTION
        "The txpDSPErrorsGroup group groups objects of TXP DSP Errors."
    ::= { mxpConfigMIBGroups 18 }



txpDSPCompensationTable OBJECT-TYPE
	SYNTAX SEQUENCE OF TxpDSPCompensationEntry
	MAX-ACCESS not-accessible
	STATUS current
	DESCRIPTION "A table containing information on TXP DSP Compensation."
::= { txpDSP 3 }

txpDSPCompensationEntry OBJECT-TYPE
	SYNTAX TxpDSPCompensationEntry
	MAX-ACCESS not-accessible
	STATUS current
	DESCRIPTION "An entry of the TXP DSP Compensation."
	INDEX { txpDSPCompensationIndex }
::= { txpDSPCompensationTable 1 }

TxpDSPCompensationEntry ::= SEQUENCE { txpDSPCompensationIndex OCTET STRING, minBulkCDCompensation OCTET STRING, maxBulkCDCompensation OCTET STRING, stepSize OCTET STRING, cdCompensation OCTET STRING }

txpDSPCompensationIndex OBJECT-TYPE
	SYNTAX OCTET STRING (SIZE(1..32))
	MAX-ACCESS not-accessible
	STATUS current
	DESCRIPTION "Reference Index for each observed process."
::= { txpDSPCompensationEntry 1 }

minBulkCDCompensation OBJECT-TYPE
	SYNTAX OCTET STRING 
	MAX-ACCESS read-only
	STATUS current
	DESCRIPTION "txp40G DSP Minimum bulk CD Compensation."
::= { txpDSPCompensationEntry 2 }

maxBulkCDCompensation OBJECT-TYPE
	SYNTAX OCTET STRING 
	MAX-ACCESS read-only
	STATUS current
	DESCRIPTION "txp40G DSP Maximum bulk CD Compensation."
::= { txpDSPCompensationEntry 3 }

stepSize OBJECT-TYPE
	SYNTAX OCTET STRING 
	MAX-ACCESS read-only
	STATUS current
	DESCRIPTION "txp40G DSP Bulk CD step size."
::= { txpDSPCompensationEntry 4 }

cdCompensation OBJECT-TYPE
	SYNTAX OCTET STRING 
	MAX-ACCESS read-only
	STATUS current
	DESCRIPTION "txp40G DSP Chromatic Dispersion Compensation."
::= { txpDSPCompensationEntry 5 }

txpDSPCompensationGroup OBJECT-GROUP
    OBJECTS { minBulkCDCompensation, maxBulkCDCompensation, stepSize, cdCompensation }
    STATUS  current
    DESCRIPTION
        "The txpDSPCompensationGroup group groups objects of TXP DSP Compensation."
    ::= { mxpConfigMIBGroups 19 }


-- mxptp status variables

trafficProcessor OBJECT IDENTIFIER ::= { mxpConfigMIBObjects 10 }

trafficProcessorTable OBJECT-TYPE
	SYNTAX SEQUENCE OF TrafficProcessorEntry
	MAX-ACCESS not-accessible
	STATUS current
	DESCRIPTION "A table containing information about traffic processor."
::= { trafficProcessor 1 }

trafficProcessorEntry OBJECT-TYPE
	SYNTAX TrafficProcessorEntry
	MAX-ACCESS not-accessible
	STATUS current
	DESCRIPTION "An entry of the Mxp."
	INDEX { trafficProcessorIndex }
::= { trafficProcessorTable 1 }

TrafficProcessorEntry ::= SEQUENCE { trafficProcessorIndex Integer32, lineFramerFsmmtrb3s Integer32, lineFramerFsmmtrb2s Integer32, lineFramerFsmmtrb1s Integer32, lineFramerFsmms Integer32, lineFramerSif Integer32, lineFramerSoof Integer32, lineFramerSlof Integer32, lineLosstatLosf Integer32, lineSecmonFlom Integer32, lineSecmonBipsfs Integer32, lineSecmonDiae Integer32, lineSecmonDbdi Integer32, lineSecmonLom Integer32, linePathmonAccstat Integer32, linePathmonMsiunst Integer32, linePathmonDais Integer32, linePathmonDlck Integer32, linePathmonDbdi Integer32, client1FramerFsmms Integer32, client1FramerFssusts Integer32, client1FramerSif Integer32, client1FramerSoof Integer32, client1FramerSlof Integer32, client1FramerFst Integer32, client1LosstatLosf Integer32, client1SecmonFlom Integer32, client1SecmonBipsfs Integer32, client1SecmonDiae Integer32, client1SecmonDbdi Integer32, client1SecmonLom Integer32, client1PathmonAccstat Integer32, client1PathmonMsiunst Integer32, client1PathmonDais Integer32, client1PathmonDlck Integer32, client1PathmonDbdi Integer32, client2FramerFsmms Integer32, client2FramerFssusts Integer32, client2FramerSif Integer32, client2FramerSoof Integer32, client2FramerSlof Integer32, client2FramerFst Integer32, client2LosstatLosf Integer32, client2SecmonFlom Integer32, client2SecmonBipsfs Integer32, client2SecmonDiae Integer32, client2SecmonDbdi Integer32, client2SecmonLom Integer32, client2PathmonAccstat Integer32, client2PathmonMsiunst Integer32, client2PathmonDais Integer32, client2PathmonDlck Integer32, client2PathmonDbdi Integer32, client3FramerFsmms Integer32, client3FramerFssusts Integer32, client3FramerSif Integer32, client3FramerSoof Integer32, client3FramerSlof Integer32, client3FramerFst Integer32, client3LosstatLosf Integer32, client3SecmonFlom Integer32, client3SecmonBipsfs Integer32, client3SecmonDiae Integer32, client3SecmonDbdi Integer32, client3SecmonLom Integer32, client3PathmonAccstat Integer32, client3PathmonMsiunst Integer32, client3PathmonDais Integer32, client3PathmonDlck Integer32, client3PathmonDbdi Integer32, client4FramerFsmms Integer32, client4FramerFssusts Integer32, client4FramerSif Integer32, client4FramerSoof Integer32, client4FramerSlof Integer32, client4FramerFst Integer32, client4LosstatLosf Integer32, client4SecmonFlom Integer32, client4SecmonBipsfs Integer32, client4SecmonDiae Integer32, client4SecmonDbdi Integer32, client4SecmonLom Integer32, client4PathmonAccstat Integer32, client4PathmonMsiunst Integer32, client4PathmonDais Integer32, client4PathmonDlck Integer32, client4PathmonDbdi Integer32}

trafficProcessorIndex OBJECT-TYPE
	SYNTAX	Integer32 (0..65535)
	MAX-ACCESS	not-accessible
	STATUS	current
	DESCRIPTION "The auxiliary variable used for identifying instances
            of the columnar objects in the txpSeverityTable"
::= { trafficProcessorEntry 1 }

lineFramerFsmmtrb3s OBJECT-TYPE
	SYNTAX      Integer32
	MAX-ACCESS  read-write
	STATUS      current
	DESCRIPTION "Line Framer FS mismatch for tributary 3"
::= { trafficProcessorEntry 2 }

lineFramerFsmmtrb2s OBJECT-TYPE
	SYNTAX      Integer32
	MAX-ACCESS  read-write
	STATUS      current
	DESCRIPTION "Line Framer FS mismatch for tributary 2"
::= { trafficProcessorEntry 3 }

lineFramerFsmmtrb1s OBJECT-TYPE
	SYNTAX      Integer32
	MAX-ACCESS  read-write
	STATUS      current
	DESCRIPTION "Line Framer FS mismatch for tributary 1"
::= { trafficProcessorEntry 4 }

lineFramerFsmms OBJECT-TYPE
	SYNTAX      Integer32
	MAX-ACCESS  read-write
	STATUS      current
	DESCRIPTION "Line Framer FS timeslot for FS mismatch"
::= { trafficProcessorEntry 5 }

lineFramerSif OBJECT-TYPE
	SYNTAX      Integer32
	MAX-ACCESS  read-write
	STATUS      current
	DESCRIPTION "Line Framer SIF status"
::= { trafficProcessorEntry 6 }

lineFramerSoof OBJECT-TYPE
	SYNTAX      Integer32
	MAX-ACCESS  read-write
	STATUS      current
	DESCRIPTION "Line Framer OOF status"
::= { trafficProcessorEntry 7 }

lineFramerSlof OBJECT-TYPE
	SYNTAX      Integer32
	MAX-ACCESS  read-write
	STATUS      current
	DESCRIPTION "Line Framer LOF status"
::= { trafficProcessorEntry 8 }

lineLosstatLosf OBJECT-TYPE
	SYNTAX      Integer32
	MAX-ACCESS  read-write
	STATUS      current
	DESCRIPTION "Line LOS status"
::= { trafficProcessorEntry 9 }

lineSecmonFlom OBJECT-TYPE
	SYNTAX      Integer32
	MAX-ACCESS  read-write
	STATUS      current
	DESCRIPTION "Line Section LOM status"
::= { trafficProcessorEntry 10 }

lineSecmonBipsfs OBJECT-TYPE
	SYNTAX      Integer32
	MAX-ACCESS  read-write
	STATUS      current
	DESCRIPTION "Line Section BIPSFS status"
::= { trafficProcessorEntry 11 }

lineSecmonDiae OBJECT-TYPE
	SYNTAX      Integer32
	MAX-ACCESS  read-write
	STATUS      current
	DESCRIPTION "Line Section DIAE status"
::= { trafficProcessorEntry 12 }

lineSecmonDbdi OBJECT-TYPE
	SYNTAX      Integer32
	MAX-ACCESS  read-write
	STATUS      current
	DESCRIPTION "Line Section DBDI status"
::= { trafficProcessorEntry 13 }

lineSecmonLom OBJECT-TYPE
	SYNTAX      Integer32
	MAX-ACCESS  read-write
	STATUS      current
	DESCRIPTION "Line Path LOM status"
::= { trafficProcessorEntry 14 }

linePathmonAccstat OBJECT-TYPE
	SYNTAX      Integer32
	MAX-ACCESS  read-write
	STATUS      current
	DESCRIPTION "Line Path LOM status"
::= { trafficProcessorEntry 15 }

linePathmonMsiunst OBJECT-TYPE
	SYNTAX      Integer32
	MAX-ACCESS  read-write
	STATUS      current
	DESCRIPTION "Line Path MSIUNST status"
::= { trafficProcessorEntry 16 }

linePathmonDais OBJECT-TYPE
	SYNTAX      Integer32
	MAX-ACCESS  read-write
	STATUS      current
	DESCRIPTION "Line Path DAIS status"
::= { trafficProcessorEntry 17 }

linePathmonDlck OBJECT-TYPE
	SYNTAX      Integer32
	MAX-ACCESS  read-write
	STATUS      current
	DESCRIPTION "Line Path DLCK status"
::= { trafficProcessorEntry 18 }

linePathmonDbdi OBJECT-TYPE
	SYNTAX      Integer32
	MAX-ACCESS  read-write
	STATUS      current
	DESCRIPTION "Line Path DLCK status"
::= { trafficProcessorEntry 19 }


client1FramerFsmms OBJECT-TYPE
	SYNTAX      Integer32
	MAX-ACCESS  read-write
	STATUS      current
	DESCRIPTION "Client 1 FS mismatch"
::= { trafficProcessorEntry 20 }

client1FramerFssusts OBJECT-TYPE
	SYNTAX      Integer32
	MAX-ACCESS  read-write
	STATUS      current
	DESCRIPTION "Client 1 FS unstable"
::= { trafficProcessorEntry 21 }

client1FramerSif OBJECT-TYPE
	SYNTAX      Integer32
	MAX-ACCESS  read-write
	STATUS      current
	DESCRIPTION "Client1 Framer SIF status"
::= { trafficProcessorEntry 22 }

client1FramerSoof OBJECT-TYPE
	SYNTAX      Integer32
	MAX-ACCESS  read-write
	STATUS      current
	DESCRIPTION "Client1 Framer OOF status"
::= { trafficProcessorEntry 23 }

client1FramerSlof OBJECT-TYPE
	SYNTAX      Integer32
	MAX-ACCESS  read-write
	STATUS      current
	DESCRIPTION "Client1 Framer LOF status"
::= { trafficProcessorEntry 24 }

client1FramerFst OBJECT-TYPE
	SYNTAX      Integer32
	MAX-ACCESS  read-write
	STATUS      current
	DESCRIPTION "Client1 Framer FST status"
::= { trafficProcessorEntry 25 }

client1LosstatLosf OBJECT-TYPE
	SYNTAX      Integer32
	MAX-ACCESS  read-write
	STATUS      current
	DESCRIPTION "Client1 LOS status"
::= { trafficProcessorEntry 26 }

client1SecmonFlom OBJECT-TYPE
	SYNTAX      Integer32
	MAX-ACCESS  read-write
	STATUS      current
	DESCRIPTION "Client1 Section LOM status"
::= { trafficProcessorEntry 27 }

client1SecmonBipsfs OBJECT-TYPE
	SYNTAX      Integer32
	MAX-ACCESS  read-write
	STATUS      current
	DESCRIPTION "Client1 Section BIPSFS status"
::= { trafficProcessorEntry 28 }

client1SecmonDiae OBJECT-TYPE
	SYNTAX      Integer32
	MAX-ACCESS  read-write
	STATUS      current
	DESCRIPTION "Client1 Section DIAE status"
::= { trafficProcessorEntry 29 }

client1SecmonDbdi OBJECT-TYPE
	SYNTAX      Integer32
	MAX-ACCESS  read-write
	STATUS      current
	DESCRIPTION "Client1 Section DBDI status"
::= { trafficProcessorEntry 30 }

client1SecmonLom OBJECT-TYPE
	SYNTAX      Integer32
	MAX-ACCESS  read-write
	STATUS      current
	DESCRIPTION "Client1 Path LOM status"
::= { trafficProcessorEntry 31 }

client1PathmonAccstat OBJECT-TYPE
	SYNTAX      Integer32
	MAX-ACCESS  read-write
	STATUS      current
	DESCRIPTION "Client1 Path LOM status"
::= { trafficProcessorEntry 32 }

client1PathmonMsiunst OBJECT-TYPE
	SYNTAX      Integer32
	MAX-ACCESS  read-write
	STATUS      current
	DESCRIPTION "Client1 Path MSIUNST status"
::= { trafficProcessorEntry 33 }

client1PathmonDais OBJECT-TYPE
	SYNTAX      Integer32
	MAX-ACCESS  read-write
	STATUS      current
	DESCRIPTION "Client1 Path DAIS status"
::= { trafficProcessorEntry 34 }

client1PathmonDlck OBJECT-TYPE
	SYNTAX      Integer32
	MAX-ACCESS  read-write
	STATUS      current
	DESCRIPTION "Client1 Path DLCK status"
::= { trafficProcessorEntry 35 }

client1PathmonDbdi OBJECT-TYPE
	SYNTAX      Integer32
	MAX-ACCESS  read-write
	STATUS      current
	DESCRIPTION "Client1 Path DLCK status"
::= { trafficProcessorEntry 36 }


client2FramerFsmms OBJECT-TYPE
	SYNTAX      Integer32
	MAX-ACCESS  read-write
	STATUS      current
	DESCRIPTION "Client 1 FS mismatch"
::= { trafficProcessorEntry 37 }

client2FramerFssusts OBJECT-TYPE
	SYNTAX      Integer32
	MAX-ACCESS  read-write
	STATUS      current
	DESCRIPTION "Client 1 FS unstable"
::= { trafficProcessorEntry 38 }

client2FramerSif OBJECT-TYPE
	SYNTAX      Integer32
	MAX-ACCESS  read-write
	STATUS      current
	DESCRIPTION "Client2 Framer SIF status"
::= { trafficProcessorEntry 39 }

client2FramerSoof OBJECT-TYPE
	SYNTAX      Integer32
	MAX-ACCESS  read-write
	STATUS      current
	DESCRIPTION "Client2 Framer OOF status"
::= { trafficProcessorEntry 40 }

client2FramerSlof OBJECT-TYPE
	SYNTAX      Integer32
	MAX-ACCESS  read-write
	STATUS      current
	DESCRIPTION "Client2 Framer LOF status"
::= { trafficProcessorEntry 41 }

client2FramerFst OBJECT-TYPE
	SYNTAX      Integer32
	MAX-ACCESS  read-write
	STATUS      current
	DESCRIPTION "Client2 Framer FST status"
::= { trafficProcessorEntry 42 }

client2LosstatLosf OBJECT-TYPE
	SYNTAX      Integer32
	MAX-ACCESS  read-write
	STATUS      current
	DESCRIPTION "Client2 LOS status"
::= { trafficProcessorEntry 43 }

client2SecmonFlom OBJECT-TYPE
	SYNTAX      Integer32
	MAX-ACCESS  read-write
	STATUS      current
	DESCRIPTION "Client2 Section LOM status"
::= { trafficProcessorEntry 44 }

client2SecmonBipsfs OBJECT-TYPE
	SYNTAX      Integer32
	MAX-ACCESS  read-write
	STATUS      current
	DESCRIPTION "Client2 Section BIPSFS status"
::= { trafficProcessorEntry 45 }

client2SecmonDiae OBJECT-TYPE
	SYNTAX      Integer32
	MAX-ACCESS  read-write
	STATUS      current
	DESCRIPTION "Client2 Section DIAE status"
::= { trafficProcessorEntry 46 }

client2SecmonDbdi OBJECT-TYPE
	SYNTAX      Integer32
	MAX-ACCESS  read-write
	STATUS      current
	DESCRIPTION "Client2 Section DBDI status"
::= { trafficProcessorEntry 47 }

client2SecmonLom OBJECT-TYPE
	SYNTAX      Integer32
	MAX-ACCESS  read-write
	STATUS      current
	DESCRIPTION "Client2 Path LOM status"
::= { trafficProcessorEntry 48 }

client2PathmonAccstat OBJECT-TYPE
	SYNTAX      Integer32
	MAX-ACCESS  read-write
	STATUS      current
	DESCRIPTION "Client2 Path LOM status"
::= { trafficProcessorEntry 49 }

client2PathmonMsiunst OBJECT-TYPE
	SYNTAX      Integer32
	MAX-ACCESS  read-write
	STATUS      current
	DESCRIPTION "Client2 Path MSIUNST status"
::= { trafficProcessorEntry 50 }

client2PathmonDais OBJECT-TYPE
	SYNTAX      Integer32
	MAX-ACCESS  read-write
	STATUS      current
	DESCRIPTION "Client2 Path DAIS status"
::= { trafficProcessorEntry 51 }

client2PathmonDlck OBJECT-TYPE
	SYNTAX      Integer32
	MAX-ACCESS  read-write
	STATUS      current
	DESCRIPTION "Client2 Path DLCK status"
::= { trafficProcessorEntry 52 }

client2PathmonDbdi OBJECT-TYPE
	SYNTAX      Integer32
	MAX-ACCESS  read-write
	STATUS      current
	DESCRIPTION "Client2 Path DLCK status"
::= { trafficProcessorEntry 53 }


client3FramerFsmms OBJECT-TYPE
	SYNTAX      Integer32
	MAX-ACCESS  read-write
	STATUS      current
	DESCRIPTION "Client 1 FS mismatch"
::= { trafficProcessorEntry 54 }

client3FramerFssusts OBJECT-TYPE
	SYNTAX      Integer32
	MAX-ACCESS  read-write
	STATUS      current
	DESCRIPTION "Client 1 FS unstable"
::= { trafficProcessorEntry 55 }

client3FramerSif OBJECT-TYPE
	SYNTAX      Integer32
	MAX-ACCESS  read-write
	STATUS      current
	DESCRIPTION "Client3 Framer SIF status"
::= { trafficProcessorEntry 56 }

client3FramerSoof OBJECT-TYPE
	SYNTAX      Integer32
	MAX-ACCESS  read-write
	STATUS      current
	DESCRIPTION "Client3 Framer OOF status"
::= { trafficProcessorEntry 57 }

client3FramerSlof OBJECT-TYPE
	SYNTAX      Integer32
	MAX-ACCESS  read-write
	STATUS      current
	DESCRIPTION "Client3 Framer LOF status"
::= { trafficProcessorEntry 58 }

client3FramerFst OBJECT-TYPE
	SYNTAX      Integer32
	MAX-ACCESS  read-write
	STATUS      current
	DESCRIPTION "Client3 Framer FST status"
::= { trafficProcessorEntry 59 }

client3LosstatLosf OBJECT-TYPE
	SYNTAX      Integer32
	MAX-ACCESS  read-write
	STATUS      current
	DESCRIPTION "Client3 LOS status"
::= { trafficProcessorEntry 60 }

client3SecmonFlom OBJECT-TYPE
	SYNTAX      Integer32
	MAX-ACCESS  read-write
	STATUS      current
	DESCRIPTION "Client3 Section LOM status"
::= { trafficProcessorEntry 61 }

client3SecmonBipsfs OBJECT-TYPE
	SYNTAX      Integer32
	MAX-ACCESS  read-write
	STATUS      current
	DESCRIPTION "Client3 Section BIPSFS status"
::= { trafficProcessorEntry 62 }

client3SecmonDiae OBJECT-TYPE
	SYNTAX      Integer32
	MAX-ACCESS  read-write
	STATUS      current
	DESCRIPTION "Client3 Section DIAE status"
::= { trafficProcessorEntry 63 }

client3SecmonDbdi OBJECT-TYPE
	SYNTAX      Integer32
	MAX-ACCESS  read-write
	STATUS      current
	DESCRIPTION "Client3 Section DBDI status"
::= { trafficProcessorEntry 64 }

client3SecmonLom OBJECT-TYPE
	SYNTAX      Integer32
	MAX-ACCESS  read-write
	STATUS      current
	DESCRIPTION "Client3 Path LOM status"
::= { trafficProcessorEntry 65 }

client3PathmonAccstat OBJECT-TYPE
	SYNTAX      Integer32
	MAX-ACCESS  read-write
	STATUS      current
	DESCRIPTION "Client3 Path LOM status"
::= { trafficProcessorEntry 66 }

client3PathmonMsiunst OBJECT-TYPE
	SYNTAX      Integer32
	MAX-ACCESS  read-write
	STATUS      current
	DESCRIPTION "Client3 Path MSIUNST status"
::= { trafficProcessorEntry 67 }

client3PathmonDais OBJECT-TYPE
	SYNTAX      Integer32
	MAX-ACCESS  read-write
	STATUS      current
	DESCRIPTION "Client3 Path DAIS status"
::= { trafficProcessorEntry 68 }

client3PathmonDlck OBJECT-TYPE
	SYNTAX      Integer32
	MAX-ACCESS  read-write
	STATUS      current
	DESCRIPTION "Client3 Path DLCK status"
::= { trafficProcessorEntry 69 }

client3PathmonDbdi OBJECT-TYPE
	SYNTAX      Integer32
	MAX-ACCESS  read-write
	STATUS      current
	DESCRIPTION "Client3 Path DLCK status"
::= { trafficProcessorEntry 70 }


client4FramerFsmms OBJECT-TYPE
	SYNTAX      Integer32
	MAX-ACCESS  read-write
	STATUS      current
	DESCRIPTION "Client 1 FS mismatch"
::= { trafficProcessorEntry 71 }

client4FramerFssusts OBJECT-TYPE
	SYNTAX      Integer32
	MAX-ACCESS  read-write
	STATUS      current
	DESCRIPTION "Client 1 FS unstable"
::= { trafficProcessorEntry 72 }

client4FramerSif OBJECT-TYPE
	SYNTAX      Integer32
	MAX-ACCESS  read-write
	STATUS      current
	DESCRIPTION "Client4 Framer SIF status"
::= { trafficProcessorEntry 73 }

client4FramerSoof OBJECT-TYPE
	SYNTAX      Integer32
	MAX-ACCESS  read-write
	STATUS      current
	DESCRIPTION "Client4 Framer OOF status"
::= { trafficProcessorEntry 74 }

client4FramerSlof OBJECT-TYPE
	SYNTAX      Integer32
	MAX-ACCESS  read-write
	STATUS      current
	DESCRIPTION "Client4 Framer LOF status"
::= { trafficProcessorEntry 75 }

client4FramerFst OBJECT-TYPE
	SYNTAX      Integer32
	MAX-ACCESS  read-write
	STATUS      current
	DESCRIPTION "Client4 Framer FST status"
::= { trafficProcessorEntry 76 }

client4LosstatLosf OBJECT-TYPE
	SYNTAX      Integer32
	MAX-ACCESS  read-write
	STATUS      current
	DESCRIPTION "Client4 LOS status"
::= { trafficProcessorEntry 77 }

client4SecmonFlom OBJECT-TYPE
	SYNTAX      Integer32
	MAX-ACCESS  read-write
	STATUS      current
	DESCRIPTION "Client4 Section LOM status"
::= { trafficProcessorEntry 78 }

client4SecmonBipsfs OBJECT-TYPE
	SYNTAX      Integer32
	MAX-ACCESS  read-write
	STATUS      current
	DESCRIPTION "Client4 Section BIPSFS status"
::= { trafficProcessorEntry 79 }

client4SecmonDiae OBJECT-TYPE
	SYNTAX      Integer32
	MAX-ACCESS  read-write
	STATUS      current
	DESCRIPTION "Client4 Section DIAE status"
::= { trafficProcessorEntry 80 }

client4SecmonDbdi OBJECT-TYPE
	SYNTAX      Integer32
	MAX-ACCESS  read-write
	STATUS      current
	DESCRIPTION "Client4 Section DBDI status"
::= { trafficProcessorEntry 81 }

client4SecmonLom OBJECT-TYPE
	SYNTAX      Integer32
	MAX-ACCESS  read-write
	STATUS      current
	DESCRIPTION "Client4 Path LOM status"
::= { trafficProcessorEntry 82 }

client4PathmonAccstat OBJECT-TYPE
	SYNTAX      Integer32
	MAX-ACCESS  read-write
	STATUS      current
	DESCRIPTION "Client4 Path LOM status"
::= { trafficProcessorEntry 83 }

client4PathmonMsiunst OBJECT-TYPE
	SYNTAX      Integer32
	MAX-ACCESS  read-write
	STATUS      current
	DESCRIPTION "Client4 Path MSIUNST status"
::= { trafficProcessorEntry 84 }

client4PathmonDais OBJECT-TYPE
	SYNTAX      Integer32
	MAX-ACCESS  read-write
	STATUS      current
	DESCRIPTION "Client4 Path DAIS status"
::= { trafficProcessorEntry 85 }

client4PathmonDlck OBJECT-TYPE
	SYNTAX      Integer32
	MAX-ACCESS  read-write
	STATUS      current
	DESCRIPTION "Client4 Path DLCK status"
::= { trafficProcessorEntry 86 }

client4PathmonDbdi OBJECT-TYPE
	SYNTAX      Integer32
	MAX-ACCESS  read-write
	STATUS      current
	DESCRIPTION "Client4 Path DLCK status"
::= { trafficProcessorEntry 87 }

mxpGroup OBJECT-GROUP
    OBJECTS { lineFramerFsmmtrb3s, lineFramerFsmmtrb2s, lineFramerFsmmtrb1s, lineFramerFsmms, lineFramerSif, lineFramerSoof, lineFramerSlof, lineLosstatLosf, lineSecmonFlom, lineSecmonBipsfs, lineSecmonDiae, lineSecmonDbdi, lineSecmonLom, linePathmonAccstat, linePathmonMsiunst, linePathmonDais, linePathmonDlck, linePathmonDbdi, client1FramerFsmms, client1FramerFssusts, client1FramerSif, client1FramerSoof, client1FramerSlof, client1FramerFst, client1LosstatLosf, client1SecmonFlom, client1SecmonBipsfs, client1SecmonDiae, client1SecmonDbdi, client1SecmonLom, client1PathmonAccstat, client1PathmonMsiunst, client1PathmonDais, client1PathmonDlck, client1PathmonDbdi, client2FramerFsmms, client2FramerFssusts, client2FramerSif, client2FramerSoof, client2FramerSlof, client2FramerFst, client2LosstatLosf, client2SecmonFlom, client2SecmonBipsfs, client2SecmonDiae, client2SecmonDbdi, client2SecmonLom, client2PathmonAccstat, client2PathmonMsiunst, client2PathmonDais, client2PathmonDlck, client2PathmonDbdi, client3FramerFsmms, client3FramerFssusts, client3FramerSif, client3FramerSoof, client3FramerSlof, client3FramerFst, client3LosstatLosf, client3SecmonFlom, client3SecmonBipsfs, client3SecmonDiae, client3SecmonDbdi, client3SecmonLom, client3PathmonAccstat, client3PathmonMsiunst, client3PathmonDais, client3PathmonDlck, client3PathmonDbdi, client4FramerFsmms, client4FramerFssusts, client4FramerSif, client4FramerSoof, client4FramerSlof, client4FramerFst, client4LosstatLosf, client4SecmonFlom, client4SecmonBipsfs, client4SecmonDiae, client4SecmonDbdi, client4SecmonLom, client4PathmonAccstat, client4PathmonMsiunst, client4PathmonDais, client4PathmonDlck, client4PathmonDbdi }
    STATUS  current
    DESCRIPTION
        "The mxp Group group groups objects mxp."
    ::= { mxpConfigMIBGroups 20 }



-- MXP Notifications MIB

mxpNotificationMIB OBJECT IDENTIFIER ::= { mxp 2 }
	mxpNotifyMIBConformance   OBJECT IDENTIFIER ::= { mxpNotificationMIB 1 }
		mxpNotifyMIBCompliances   OBJECT IDENTIFIER ::= { mxpNotifyMIBConformance 1 }		
		mxpNotifyGroups             OBJECT IDENTIFIER ::= { mxpNotifyMIBConformance 2 }
		mxpNotificationGroups       OBJECT IDENTIFIER ::= { mxpNotifyMIBConformance 3 }
	mxpMIBNotifications         OBJECT IDENTIFIER ::= { mxpNotificationMIB 2 }
		mxpMIBNotificationPrefix    OBJECT IDENTIFIER ::= { mxpMIBNotifications 0 }
		mxpMIBNotifyObjects         OBJECT IDENTIFIER ::= { mxpMIBNotifications 1 }

mxpNotifyCompliance MODULE-COMPLIANCE
    STATUS  current
    DESCRIPTION
            "The compliance statement for notify entities which
            implement this MIB module."
    MODULE  -- this module
        MANDATORY-GROUPS {  edfaNotifyGroup, edfaNotificationGroup,
                            txpNotifyGroup, txpNotificationGroup,
                            xfp1NotifyGroup, xfp1NotificationGroup,
                            xfp2NotifyGroup, xfp2NotificationGroup,
                            xfp3NotifyGroup, xfp3NotificationGroup,
                            xfp4NotifyGroup, xfp4NotificationGroup,
                            tpNotifyGroup, tpNotificationGroup
                            }

    ::= { mxpNotifyMIBCompliances 1 }

--
-- Table for edfa
--

edfaNotifyTable OBJECT-TYPE
	SYNTAX SEQUENCE OF EdfaNotifyEntry
	MAX-ACCESS not-accessible
	STATUS current
	DESCRIPTION "A table containing information on EDFA notification."
::= { mxpMIBNotifyObjects 1 }

edfaNotifyEntry OBJECT-TYPE
	SYNTAX	EdfaNotifyEntry
	MAX-ACCESS	not-accessible
	STATUS	current
	DESCRIPTION "An entry of the EDFA notification table."
	INDEX	{ edfaNotifyIndex }
::= { edfaNotifyTable  1 }

EdfaNotifyEntry ::= SEQUENCE { edfaNotifyIndex Integer32, edfaNotifyAmpStatus Integer32, edfaNotifyInputPower Integer32, edfaNotifyLop Integer32, 
 edfaNotifyLos Integer32, edfaNotifyOutPow Integer32, edfaNotifyTemp Integer32}

edfaNotifyIndex OBJECT-TYPE
	SYNTAX	Integer32 (0..65535)
	MAX-ACCESS	not-accessible
	STATUS	current
	DESCRIPTION "The auxiliary variable used for identifying instances of the columnar objects in the edfaNotifyTable."
::= { edfaNotifyEntry 1 }

edfaNotifyAmpStatus OBJECT-TYPE
	SYNTAX      Integer32
	MAX-ACCESS  read-only
	STATUS      current
	DESCRIPTION "EDFA Amp. Status alarm Notify."
::= { edfaNotifyEntry 2 }

edfaNotifyAmpStatusNotification NOTIFICATION-TYPE
    OBJECTS { edfaNotifyAmpStatus }
    STATUS current
    DESCRIPTION "Notification of EDFA Amp. status alarm Notify."
::= { mxpMIBNotificationPrefix 1 }

edfaNotifyInputPower OBJECT-TYPE
	SYNTAX      Integer32
	MAX-ACCESS  read-only
	STATUS      current
	DESCRIPTION "EDFA Input Power alarm Notify."
::= { edfaNotifyEntry 3 }

edfaNotifyInputPowerNotification NOTIFICATION-TYPE
    OBJECTS { edfaNotifyInputPower }
    STATUS current
    DESCRIPTION "Notification of EDFA Input Power alarm Notify."
::= { mxpMIBNotificationPrefix 2 }

edfaNotifyLop OBJECT-TYPE
	SYNTAX      Integer32
	MAX-ACCESS  read-only
	STATUS      current
	DESCRIPTION "EDFA LOP alarm Notify."
::= { edfaNotifyEntry 4 }

edfaNotifyLopNotification NOTIFICATION-TYPE
    OBJECTS { edfaNotifyLop }
    STATUS current
    DESCRIPTION "Notification of EDFA LOP alarm Notify."
::= { mxpMIBNotificationPrefix 3 }

edfaNotifyLos OBJECT-TYPE
	SYNTAX      Integer32
	MAX-ACCESS  read-only
	STATUS      current
	DESCRIPTION "EDFA LOS alarm Notify."
::= { edfaNotifyEntry 5 }

edfaNotifyLosNotification NOTIFICATION-TYPE
    OBJECTS { edfaNotifyLos }
    STATUS current
    DESCRIPTION "Notification of EDFA LOS alarm Notify."
::= { mxpMIBNotificationPrefix 4 }

edfaNotifyOutPow OBJECT-TYPE
	SYNTAX      Integer32
	MAX-ACCESS  read-only
	STATUS      current
	DESCRIPTION "EDFA Output Power alarm Notify."
::= { edfaNotifyEntry 6 }

edfaNotifyOutPowNotification NOTIFICATION-TYPE
    OBJECTS { edfaNotifyOutPow }
    STATUS current
    DESCRIPTION "Notification of EDFA Output Power alarm Notify."
::= { mxpMIBNotificationPrefix 5 }

edfaNotifyTemp OBJECT-TYPE
	SYNTAX      Integer32
	MAX-ACCESS  read-only
	STATUS      current
	DESCRIPTION "EDFA Temperature alarm Notify."
::= { edfaNotifyEntry 7 }

edfaNotifyTempNotification NOTIFICATION-TYPE
    OBJECTS { edfaNotifyTemp }
    STATUS current
    DESCRIPTION "Notification of EDFA Temperature alarm Notify."
::= { mxpMIBNotificationPrefix 6 }

edfaNotifyGroup OBJECT-GROUP
    OBJECTS { edfaNotifyAmpStatus, edfaNotifyInputPower, edfaNotifyLop, edfaNotifyLos, edfaNotifyOutPow, edfaNotifyTemp }
    STATUS  current
    DESCRIPTION
        "The edfaNotifyGroup, groups objects of EDFA."
    ::= { mxpNotifyGroups 1 }

edfaNotificationGroup NOTIFICATION-GROUP
    NOTIFICATIONS { edfaNotifyAmpStatusNotification, edfaNotifyInputPowerNotification, edfaNotifyLopNotification, edfaNotifyLosNotification, edfaNotifyOutPowNotification, edfaNotifyTempNotification }
    STATUS  current
    DESCRIPTION
        "The edfaNotificationGroup, groups notifications of EDFA."
    ::= { mxpNotificationGroups 1 }

--
-- Table for TXP
--

txpNotifyTable OBJECT-TYPE
	SYNTAX SEQUENCE OF TxpNotifyEntry
	MAX-ACCESS not-accessible
	STATUS current
	DESCRIPTION "A table containing information on TXP."
::= { mxpMIBNotifyObjects 2 }

txpNotifyEntry OBJECT-TYPE
	SYNTAX	TxpNotifyEntry
	MAX-ACCESS	not-accessible
	STATUS	current
	DESCRIPTION "An entry of the TXP notification table."
	INDEX	{ txpNotifyIndex }
::= { txpNotifyTable  1 }

TxpNotifyEntry ::= SEQUENCE {	txpNotifyIndex Integer32, 
								txpNotifyEol Integer32, 
								txpNotifyModTemp Integer32, 
								txpNotifyTxooa Integer32, 
								txpNotifyTxLof Integer32,
								txpNotifyTxDsc Integer32, 
								txpNotifyLsWav Integer32, 
								txpNotifyLsBias Integer32, 
								txpNotifyLsTemp Integer32, 
								txpNotifyTxLock Integer32, 
								txpNotifyLsPow Integer32,
								txpNotifyModBias Integer32,
								txpNotifyLatTxFifo Integer32, 
								txpNotifyRxPow Integer32, 
								txpNotifyRxLos Integer32, 
								txpNotifyRxLock Integer32, 
								txpNotifyRxs Integer32,
								txpNotifyPrbsErr Integer32, 
								txpNotifyPsummary Integer32, 
								txpNotifyP5vAnalog Integer32, 
								txpNotifyN5v2Analog Integer32, 
								txpNotifyP3p3vAnalog Integer32,
								txpNotifyP3p3vDigital Integer32, 
								txpNotifyLvDigital Integer32, 
								txpNotifyN5p2vDigital Integer32
							}

txpNotifyIndex OBJECT-TYPE
	SYNTAX	Integer32 (0..65535)
	MAX-ACCESS	not-accessible
	STATUS	current
	DESCRIPTION "The auxiliary variable used for identifying instances of the columnar objects in the txpNotifyTable."
::= { txpNotifyEntry 1 }

txpNotifyEol OBJECT-TYPE
	SYNTAX      Integer32
	MAX-ACCESS  read-write
	STATUS      current
	DESCRIPTION "TXP Eol alarm Notify."
::= { txpNotifyEntry 2 }

txpNotifyEolNotification NOTIFICATION-TYPE
    OBJECTS { txpNotifyEol }
    STATUS current
    DESCRIPTION "Notification of EDFA Eol alarm Notify."
::= { mxpMIBNotificationPrefix 7 }

txpNotifyModTemp OBJECT-TYPE
	SYNTAX      Integer32
	MAX-ACCESS  read-write
	STATUS      current
	DESCRIPTION "TXP Module Temperature alarm Notify."
::= { txpNotifyEntry 3 }

txpNotifyModTempNotification NOTIFICATION-TYPE
    OBJECTS { txpNotifyModTemp }
    STATUS current
    DESCRIPTION "Notification of EDFA Module Temperature alarm Notify."
::= { mxpMIBNotificationPrefix 8 }

txpNotifyTxooa OBJECT-TYPE
	SYNTAX      Integer32
	MAX-ACCESS  read-write
	STATUS      current
	DESCRIPTION "TXP Txooa alarm Notify."
::= { txpNotifyEntry 4 }

txpNotifyTxooaNotification NOTIFICATION-TYPE
    OBJECTS { txpNotifyTxooa }
    STATUS current
    DESCRIPTION "Notification of EDFA Txooa alarm Notify."
::= { mxpMIBNotificationPrefix 9 }

txpNotifyTxLof OBJECT-TYPE
	SYNTAX      Integer32
	MAX-ACCESS  read-write
	STATUS      current
	DESCRIPTION "TXP Lof alarm Notify."
::= { txpNotifyEntry 5 }

txpNotifyTxLofNotification NOTIFICATION-TYPE
    OBJECTS { txpNotifyTxLof }
    STATUS current
    DESCRIPTION "Notification of TXP TxLof alarm Notify."
::= { mxpMIBNotificationPrefix 10 }

txpNotifyTxDsc OBJECT-TYPE
	SYNTAX      Integer32
	MAX-ACCESS  read-write
	STATUS      current
	DESCRIPTION "TXP TxDsc alarm Notify."
::= { txpNotifyEntry 6 }

txpNotifyTxDscNotification NOTIFICATION-TYPE
    OBJECTS { txpNotifyTxDsc }
    STATUS current
    DESCRIPTION "Notification of TXP TxDsc alarm Notify."
::= { mxpMIBNotificationPrefix 11 }

txpNotifyLsWav OBJECT-TYPE
	SYNTAX      Integer32
	MAX-ACCESS  read-write
	STATUS      current
	DESCRIPTION "TXP LsWav alarm Notify."
::= { txpNotifyEntry 7 }

txpNotifyLsWavNotification NOTIFICATION-TYPE
    OBJECTS { txpNotifyLsWav }
    STATUS current
    DESCRIPTION "Notification of TXP LsWav alarm Notify."
::= { mxpMIBNotificationPrefix 12 }

txpNotifyLsBias OBJECT-TYPE
	SYNTAX      Integer32
	MAX-ACCESS  read-write
	STATUS      current
	DESCRIPTION "TXP LsBias alarm Notify."
::= { txpNotifyEntry 8 }

txpNotifyLsBiasNotification NOTIFICATION-TYPE
    OBJECTS { txpNotifyLsBias }
    STATUS current
    DESCRIPTION "Notification of TXP LsBias alarm Notify."
::= { mxpMIBNotificationPrefix 13 }

txpNotifyLsTemp OBJECT-TYPE
	SYNTAX      Integer32
	MAX-ACCESS  read-write
	STATUS      current
	DESCRIPTION "TXP LsTemp alarm Notify."
::= { txpNotifyEntry 9 }

txpNotifyLsTempNotification NOTIFICATION-TYPE
    OBJECTS { txpNotifyLsTemp }
    STATUS current
    DESCRIPTION "Notification of TXP LsTemp alarm Notify."
::= { mxpMIBNotificationPrefix 14 }

txpNotifyTxLock OBJECT-TYPE
	SYNTAX      Integer32
	MAX-ACCESS  read-write
	STATUS      current
	DESCRIPTION "TXP TxLock alarm Notify."
::= { txpNotifyEntry 10 }

txpNotifyTxLockNotification NOTIFICATION-TYPE
    OBJECTS { txpNotifyTxLock }
    STATUS current
    DESCRIPTION "Notification of TXP TxLock alarm Notify."
::= { mxpMIBNotificationPrefix 15 }

txpNotifyLsPow OBJECT-TYPE
	SYNTAX      Integer32
	MAX-ACCESS  read-write
	STATUS      current
	DESCRIPTION "TXP LsPow alarm Notify."
::= { txpNotifyEntry 11 }

txpNotifyLsPowNotification NOTIFICATION-TYPE
    OBJECTS { txpNotifyLsPow }
    STATUS current
    DESCRIPTION "Notification of TXP LsPow alarm Notify."
::= { mxpMIBNotificationPrefix 16 }

txpNotifyModBias OBJECT-TYPE
	SYNTAX      Integer32
	MAX-ACCESS  read-write
	STATUS      current
	DESCRIPTION "TXP ModBias alarm Notify."
::= { txpNotifyEntry 12 }

txpNotifyModBiasNotification NOTIFICATION-TYPE
    OBJECTS { txpNotifyModBias }
    STATUS current
    DESCRIPTION "Notification of TXP ModBias alarm Notify."
::= { mxpMIBNotificationPrefix 17 }

txpNotifyLatTxFifo OBJECT-TYPE
	SYNTAX      Integer32
	MAX-ACCESS  read-write
	STATUS      current
	DESCRIPTION "TXP LatTxFifo alarm Notify."
::= { txpNotifyEntry 13 }

txpNotifyLatTxFifoNotification NOTIFICATION-TYPE
    OBJECTS { txpNotifyLatTxFifo }
    STATUS current
    DESCRIPTION "Notification of TXP LatTxFifo alarm Notify."
::= { mxpMIBNotificationPrefix 18 }

txpNotifyRxPow OBJECT-TYPE
	SYNTAX      Integer32
	MAX-ACCESS  read-write
	STATUS      current
	DESCRIPTION "TXP RxPow alarm Notify."
::= { txpNotifyEntry 14 }

txpNotifyRxPowNotification NOTIFICATION-TYPE
    OBJECTS { txpNotifyRxPow }
    STATUS current
    DESCRIPTION "Notification of TXP RxPow alarm Notify."
::= { mxpMIBNotificationPrefix 19 }

txpNotifyRxLos OBJECT-TYPE
	SYNTAX      Integer32
	MAX-ACCESS  read-write
	STATUS      current
	DESCRIPTION "TXP RxLos alarm Notify."
::= { txpNotifyEntry 15 }

txpNotifyRxLosNotification NOTIFICATION-TYPE
    OBJECTS { txpNotifyRxLos }
    STATUS current
    DESCRIPTION "Notification of TXP RxLos alarm Notify."
::= { mxpMIBNotificationPrefix 20 }

txpNotifyRxLock OBJECT-TYPE
	SYNTAX      Integer32
	MAX-ACCESS  read-write
	STATUS      current
	DESCRIPTION "TXP RxLock alarm Notify."
::= { txpNotifyEntry 16 }

txpNotifyRxLockNotification NOTIFICATION-TYPE
    OBJECTS { txpNotifyRxLock }
    STATUS current
    DESCRIPTION "Notification of TXP RxLock alarm Notify."
::= { mxpMIBNotificationPrefix 21 }

txpNotifyRxs OBJECT-TYPE
	SYNTAX      Integer32
	MAX-ACCESS  read-write
	STATUS      current
	DESCRIPTION "TXP Rxs alarm Notify."
::= { txpNotifyEntry 17 }

txpNotifyRxsNotification NOTIFICATION-TYPE
    OBJECTS { txpNotifyRxs }
    STATUS current
    DESCRIPTION "Notification of TXP Rxs alarm Notify."
::= { mxpMIBNotificationPrefix 22 }

txpNotifyPrbsErr OBJECT-TYPE
	SYNTAX      Integer32
	MAX-ACCESS  read-write
	STATUS      current
	DESCRIPTION "TXP PrbsErr alarm Notify."
::= { txpNotifyEntry 18 }

txpNotifyPrbsErrNotification NOTIFICATION-TYPE
    OBJECTS { txpNotifyPrbsErr }
    STATUS current
    DESCRIPTION "Notification of TXP PrbsErr alarm Notify."
::= { mxpMIBNotificationPrefix 23 }

txpNotifyPsummary OBJECT-TYPE
	SYNTAX      Integer32
	MAX-ACCESS  read-write
	STATUS      current
	DESCRIPTION "TXP Psummary alarm Notify."
::= { txpNotifyEntry 19 }

txpNotifyPsummaryNotification NOTIFICATION-TYPE
    OBJECTS { txpNotifyPsummary }
    STATUS current
    DESCRIPTION "Notification of TXP Psummary alarm Notify."
::= { mxpMIBNotificationPrefix 24 }

txpNotifyP5vAnalog OBJECT-TYPE
	SYNTAX      Integer32
	MAX-ACCESS  read-write
	STATUS      current
	DESCRIPTION "TXP P5vAnalog alarm Notify."
::= { txpNotifyEntry 20 }

txpNotifyP5vAnalogNotification NOTIFICATION-TYPE
    OBJECTS { txpNotifyP5vAnalog }
    STATUS current
    DESCRIPTION "Notification of TXP P5vAnalog alarm Notify."
::= { mxpMIBNotificationPrefix 25 }

txpNotifyN5v2Analog OBJECT-TYPE
	SYNTAX      Integer32
	MAX-ACCESS  read-write
	STATUS      current
	DESCRIPTION "TXP N5v2Analog alarm Notify."
::= { txpNotifyEntry 21 }

txpNotifyN5v2AnalogNotification NOTIFICATION-TYPE
    OBJECTS { txpNotifyN5v2Analog }
    STATUS current
    DESCRIPTION "Notification of TXP N5v2Analog alarm Notify."
::= { mxpMIBNotificationPrefix 26 }

txpNotifyP3p3vAnalog OBJECT-TYPE
	SYNTAX      Integer32
	MAX-ACCESS  read-write
	STATUS      current
	DESCRIPTION "TXP P3p3vAnalog alarm Notify."
::= { txpNotifyEntry 22 }

txpNotifyP3p3vAnalogNotification NOTIFICATION-TYPE
    OBJECTS { txpNotifyP3p3vAnalog }
    STATUS current
    DESCRIPTION "Notification of TXP P3p3vAnalog alarm Notify."
::= { mxpMIBNotificationPrefix 27 }

txpNotifyP3p3vDigital OBJECT-TYPE
	SYNTAX      Integer32
	MAX-ACCESS  read-write
	STATUS      current
	DESCRIPTION "TXP P3p3vDigital alarm Notify."
::= { txpNotifyEntry 23 }

txpNotifyP3p3vDigNotification NOTIFICATION-TYPE
    OBJECTS { txpNotifyP3p3vDigital }
    STATUS current
    DESCRIPTION "Notification of TXP P3p3vDigital alarm Notify."
::= { mxpMIBNotificationPrefix 28 }

txpNotifyLvDigital OBJECT-TYPE
	SYNTAX      Integer32
	MAX-ACCESS  read-write
	STATUS      current
	DESCRIPTION "TXP LvDigital alarm Notify."
::= { txpNotifyEntry 24 }

txpNotifyLvDigitalNotification NOTIFICATION-TYPE
    OBJECTS { txpNotifyLvDigital }
    STATUS current
    DESCRIPTION "Notification of TXP LvDigital alarm Notify."
::= { mxpMIBNotificationPrefix 29 }

txpNotifyN5p2vDigital OBJECT-TYPE
	SYNTAX      Integer32
	MAX-ACCESS  read-write
	STATUS      current
	DESCRIPTION "TXP N5p2vDigital alarm Notify."
::= { txpNotifyEntry 25 }

txpNotifyN5p2vDigNotification NOTIFICATION-TYPE
    OBJECTS { txpNotifyN5p2vDigital }
    STATUS current
    DESCRIPTION "Notification of TXP N5p2vDigital alarm Notify."
::= { mxpMIBNotificationPrefix 30 }

txpNotifyGroup OBJECT-GROUP
    OBJECTS { 	txpNotifyEol, 
    			txpNotifyModTemp, 
    			txpNotifyTxooa, 
    			txpNotifyTxLof, 
    			txpNotifyTxDsc, 
    			txpNotifyLsWav, 
    			txpNotifyLsBias, 
    			txpNotifyLsTemp, 
    			txpNotifyTxLock, 
    			txpNotifyLsPow, 
    			txpNotifyModBias, 
    			txpNotifyLatTxFifo, 
    			txpNotifyRxPow, 
    			txpNotifyRxLos, 
    			txpNotifyRxLock, 
    			txpNotifyRxs, 
    			txpNotifyPrbsErr, 
    			txpNotifyPsummary, 
    			txpNotifyP5vAnalog, 
    			txpNotifyN5v2Analog, 
    			txpNotifyP3p3vAnalog, 
    			txpNotifyP3p3vDigital, 
    			txpNotifyLvDigital, 
    			txpNotifyN5p2vDigital}
    STATUS  current
    DESCRIPTION
        "The txpNotifyGroup, groups objects of txp."
    ::= { mxpNotifyGroups 2 }

txpNotificationGroup NOTIFICATION-GROUP
    NOTIFICATIONS {	txpNotifyEolNotification, 
    				txpNotifyModTempNotification, 
    				txpNotifyTxooaNotification, 
    				txpNotifyTxLofNotification, 
    				txpNotifyTxDscNotification, 
    				txpNotifyLsWavNotification, 
    				txpNotifyLsBiasNotification, 
    				txpNotifyLsTempNotification, 
    				txpNotifyTxLockNotification, 
    				txpNotifyLsPowNotification, 
    				txpNotifyModBiasNotification, 
    				txpNotifyLatTxFifoNotification, 
    				txpNotifyRxPowNotification, 
    				txpNotifyRxLosNotification, 
    				txpNotifyRxLockNotification, 
    				txpNotifyRxsNotification, 
    				txpNotifyPrbsErrNotification, 
    				txpNotifyPsummaryNotification, 
    				txpNotifyP5vAnalogNotification, 
    				txpNotifyN5v2AnalogNotification, 
    				txpNotifyP3p3vAnalogNotification, 
    				txpNotifyP3p3vDigNotification, 
    				txpNotifyLvDigitalNotification, 
    				txpNotifyN5p2vDigNotification
    			}
    STATUS  current
    DESCRIPTION
        "The txpNotificationGroup, groups notifications of txp."
    ::= { mxpNotificationGroups 2 }

--
-- Table for xfp1Notify
--

xfp1NotifyTable OBJECT-TYPE
	SYNTAX SEQUENCE OF XFP1NotifyEntry
	MAX-ACCESS not-accessible
	STATUS current
	DESCRIPTION "A table containing information on xfp1Notify."
::= { mxpMIBNotifyObjects 3 }

xfp1NotifyEntry OBJECT-TYPE
	SYNTAX	XFP1NotifyEntry
	MAX-ACCESS	not-accessible
	STATUS	current
	DESCRIPTION "An entry of the xfp1Notify table."
	INDEX	{ xfp1NotifyIndex }
::= { xfp1NotifyTable  1 }

XFP1NotifyEntry ::= SEQUENCE { xfp1NotifyIndex Integer32, xfp1NotifyPresence Integer32, xfp1NotifyRxLoss Integer32, xfp1NotifyReady Integer32,
 xfp1NotifyTxPower Integer32, xfp1NotifyRxPower Integer32, xfp1NotifyTemperature Integer32, xfp1NotifyLowTxPower Integer32, xfp1NotifyHighTxPower Integer32, 
 xfp1NotifyLowRxPower Integer32, xfp1NotifyHighRxPower Integer32, xfp1NotifyRxCdrLossOfLock Integer32, xfp1NotifyTxCdrLossOfLock Integer32, xfp1NotifyLaserFault Integer32}

xfp1NotifyIndex OBJECT-TYPE
	SYNTAX	Integer32 (0..65535)
	MAX-ACCESS	not-accessible
	STATUS	current
	DESCRIPTION "The auxiliary variable used for identifying instances
            of the columnar objects in the xfpTable"
::= { xfp1NotifyEntry 1 }

xfp1NotifyPresence OBJECT-TYPE
	SYNTAX      Integer32
	MAX-ACCESS  read-write
	STATUS      current
	DESCRIPTION "alarm Notify"
::= { xfp1NotifyEntry 2 }

xfp1NotifyPresenceNotification NOTIFICATION-TYPE
    OBJECTS { xfp1NotifyPresence }
    STATUS current
    DESCRIPTION "Notification of XFP1 Presence Notify."
::= { mxpMIBNotificationPrefix 31 }

xfp1NotifyRxLoss OBJECT-TYPE
	SYNTAX      Integer32
	MAX-ACCESS  read-write
	STATUS      current
	DESCRIPTION "alarm Notify"
::= { xfp1NotifyEntry 3 }

xfp1NotifyRxLossNotification NOTIFICATION-TYPE
    OBJECTS { xfp1NotifyRxLoss }
    STATUS current
    DESCRIPTION "Notification of XFP1 RxLoss Notify."
::= { mxpMIBNotificationPrefix 32 }

xfp1NotifyReady OBJECT-TYPE
	SYNTAX      Integer32
	MAX-ACCESS  read-write
	STATUS      current
	DESCRIPTION "alarm Notify"
::= { xfp1NotifyEntry 4 }

xfp1NotifyReadyNotification NOTIFICATION-TYPE
    OBJECTS { xfp1NotifyReady }
    STATUS current
    DESCRIPTION "Notification of XFP1 Ready Notify."
::= { mxpMIBNotificationPrefix 33 }

xfp1NotifyTxPower OBJECT-TYPE
	SYNTAX      Integer32
	MAX-ACCESS  read-write
	STATUS      current
	DESCRIPTION "alarm Notify"
::= { xfp1NotifyEntry 5 }

xfp1NotifyTxPowerNotification NOTIFICATION-TYPE
    OBJECTS { xfp1NotifyTxPower }
    STATUS current
    DESCRIPTION "Notification of XFP1 TxPower Notify."
::= { mxpMIBNotificationPrefix 34 }

xfp1NotifyRxPower OBJECT-TYPE
	SYNTAX      Integer32
	MAX-ACCESS  read-write
	STATUS      current
	DESCRIPTION "alarm Notify"
::= { xfp1NotifyEntry 6 }

xfp1NotifyRxPowerNotification NOTIFICATION-TYPE
    OBJECTS { xfp1NotifyRxPower }
    STATUS current
    DESCRIPTION "Notification of XFP1 Power Notify."
::= { mxpMIBNotificationPrefix 35 }

xfp1NotifyTemperature OBJECT-TYPE
	SYNTAX      Integer32
	MAX-ACCESS  read-write
	STATUS      current
	DESCRIPTION "alarm Notify"
::= { xfp1NotifyEntry 7 }

xfp1NotifyTempNotification NOTIFICATION-TYPE
    OBJECTS { xfp1NotifyTemperature }
    STATUS current
    DESCRIPTION "Notification of XFP1 Temperature Notify."
::= { mxpMIBNotificationPrefix 36 }

xfp1NotifyLowTxPower OBJECT-TYPE
	SYNTAX      Integer32
	MAX-ACCESS  read-write
	STATUS      current
	DESCRIPTION "alarm Notify"
::= { xfp1NotifyEntry 8 }

xfp1NotifyLowTxPowNotification NOTIFICATION-TYPE
    OBJECTS { xfp1NotifyLowTxPower }
    STATUS current
    DESCRIPTION "Notification of XFP1 LowTxPower Notify."
::= { mxpMIBNotificationPrefix 37 }

xfp1NotifyHighTxPower OBJECT-TYPE
	SYNTAX      Integer32
	MAX-ACCESS  read-write
	STATUS      current
	DESCRIPTION "alarm Notify"
::= { xfp1NotifyEntry 9 }

xfp1NotifyHighTxPowNotification NOTIFICATION-TYPE
    OBJECTS { xfp1NotifyHighTxPower }
    STATUS current
    DESCRIPTION "Notification of XFP1 HighTxPower Notify."
::= { mxpMIBNotificationPrefix 38 }

xfp1NotifyLowRxPower OBJECT-TYPE
	SYNTAX      Integer32
	MAX-ACCESS  read-write
	STATUS      current
	DESCRIPTION "alarm Notify"
::= { xfp1NotifyEntry 10 }

xfp1NotifyLowRxPowNotification NOTIFICATION-TYPE
    OBJECTS { xfp1NotifyLowRxPower }
    STATUS current
    DESCRIPTION "Notification of XFP1 LowRxPower Notify."
::= { mxpMIBNotificationPrefix 39 }

xfp1NotifyHighRxPower OBJECT-TYPE
	SYNTAX      Integer32
	MAX-ACCESS  read-write
	STATUS      current
	DESCRIPTION "alarm Notify"
::= { xfp1NotifyEntry 11 }

xfp1NotifyHighRxPowNotification NOTIFICATION-TYPE
    OBJECTS { xfp1NotifyHighRxPower }
    STATUS current
    DESCRIPTION "Notification of XFP1 HighRxPower Notify."
::= { mxpMIBNotificationPrefix 40 }

xfp1NotifyRxCdrLossOfLock OBJECT-TYPE
	SYNTAX      Integer32
	MAX-ACCESS  read-write
	STATUS      current
	DESCRIPTION "alarm Notify"
::= { xfp1NotifyEntry 12 }

xfp1NotifyRxCdrLOLNotification NOTIFICATION-TYPE
    OBJECTS { xfp1NotifyRxCdrLossOfLock }
    STATUS current
    DESCRIPTION "Notification of XFP1 RxCdrLossOfLock Notify."
::= { mxpMIBNotificationPrefix 41 }

xfp1NotifyTxCdrLossOfLock OBJECT-TYPE
	SYNTAX      Integer32
	MAX-ACCESS  read-write
	STATUS      current
	DESCRIPTION "alarm Notify"
::= { xfp1NotifyEntry 13 }

xfp1NotifyTxCdrLOLNotification NOTIFICATION-TYPE
    OBJECTS { xfp1NotifyTxCdrLossOfLock }
    STATUS current
    DESCRIPTION "Notification of XFP1 TxCdrLossOfLock Notify."
::= { mxpMIBNotificationPrefix 42 }

xfp1NotifyLaserFault OBJECT-TYPE
	SYNTAX      Integer32
	MAX-ACCESS  read-write
	STATUS      current
	DESCRIPTION "alarm Notify"
::= { xfp1NotifyEntry 14 }

xfp1NotifyLaserFaultNotification NOTIFICATION-TYPE
    OBJECTS { xfp1NotifyLaserFault }
    STATUS current
    DESCRIPTION "Notification of XFP1 LaserFault Notify."
::= { mxpMIBNotificationPrefix 43 }

xfp1NotifyGroup OBJECT-GROUP
    OBJECTS { xfp1NotifyPresence, xfp1NotifyRxLoss, xfp1NotifyReady, xfp1NotifyTxPower, xfp1NotifyRxPower, 
    xfp1NotifyTemperature, xfp1NotifyLowTxPower, xfp1NotifyHighTxPower, xfp1NotifyLowRxPower, 
    xfp1NotifyHighRxPower, xfp1NotifyRxCdrLossOfLock, xfp1NotifyTxCdrLossOfLock, xfp1NotifyLaserFault }
    STATUS  current
    DESCRIPTION
        "The xfp1NotifyGroup, groups objects of xfp1Notify."
    ::= { mxpNotifyGroups 3 }

xfp1NotificationGroup NOTIFICATION-GROUP
    NOTIFICATIONS { xfp1NotifyPresenceNotification, xfp1NotifyRxLossNotification, xfp1NotifyReadyNotification, xfp1NotifyTxPowerNotification, xfp1NotifyRxPowerNotification, xfp1NotifyTempNotification, xfp1NotifyLowTxPowNotification, xfp1NotifyHighTxPowNotification, xfp1NotifyLowRxPowNotification, xfp1NotifyHighRxPowNotification, xfp1NotifyRxCdrLOLNotification, xfp1NotifyTxCdrLOLNotification, xfp1NotifyLaserFaultNotification }
    STATUS  current
    DESCRIPTION "The xfp1NotificationGroup, groups notifications of XFP1."
    ::= { mxpNotificationGroups 3 }

--
-- Table for xfp2Notify
--

xfp2NotifyTable OBJECT-TYPE
	SYNTAX SEQUENCE OF XFP2NotifyEntry
	MAX-ACCESS not-accessible
	STATUS current
	DESCRIPTION "A table containing information on xfp2Notify."
::= { mxpMIBNotifyObjects 4 }

xfp2NotifyEntry OBJECT-TYPE
	SYNTAX	XFP2NotifyEntry
	MAX-ACCESS	not-accessible
	STATUS	current
	DESCRIPTION "An entry of the xfp2Notify table."
	INDEX	{ xfp2NotifyIndex }
::= { xfp2NotifyTable  1 }

XFP2NotifyEntry ::= SEQUENCE { xfp2NotifyIndex Integer32, xfp2NotifyPresence Integer32, xfp2NotifyRxLoss Integer32, xfp2NotifyReady Integer32,
 xfp2NotifyTxPower Integer32, xfp2NotifyRxPower Integer32, xfp2NotifyTemperature Integer32, xfp2NotifyLowTxPower Integer32, xfp2NotifyHighTxPower Integer32, 
 xfp2NotifyLowRxPower Integer32, xfp2NotifyHighRxPower Integer32, xfp2NotifyRxCdrLossOfLock Integer32, xfp2NotifyTxCdrLossOfLock Integer32, xfp2NotifyLaserFault Integer32}

xfp2NotifyIndex OBJECT-TYPE
	SYNTAX	Integer32 (0..65535)
	MAX-ACCESS	not-accessible
	STATUS	current
	DESCRIPTION "The auxiliary variable used for identifying instances
            of the columnar objects in the xfpTable"
::= { xfp2NotifyEntry 1 }

xfp2NotifyPresence OBJECT-TYPE
	SYNTAX      Integer32
	MAX-ACCESS  read-write
	STATUS      current
	DESCRIPTION "alarm Notify"
::= { xfp2NotifyEntry 2 }

xfp2NotifyPresenceNotification NOTIFICATION-TYPE
    OBJECTS { xfp2NotifyPresence }
    STATUS current
    DESCRIPTION "Notification of xfp2 Presence Notify."
::= { mxpMIBNotificationPrefix 44 }

xfp2NotifyRxLoss OBJECT-TYPE
	SYNTAX      Integer32
	MAX-ACCESS  read-write
	STATUS      current
	DESCRIPTION "alarm Notify"
::= { xfp2NotifyEntry 3 }

xfp2NotifyRxLossNotification NOTIFICATION-TYPE
    OBJECTS { xfp2NotifyRxLoss }
    STATUS current
    DESCRIPTION "Notification of xfp2 RxLoss Notify."
::= { mxpMIBNotificationPrefix 45 }

xfp2NotifyReady OBJECT-TYPE
	SYNTAX      Integer32
	MAX-ACCESS  read-write
	STATUS      current
	DESCRIPTION "alarm Notify"
::= { xfp2NotifyEntry 4 }

xfp2NotifyReadyNotification NOTIFICATION-TYPE
    OBJECTS { xfp2NotifyReady }
    STATUS current
    DESCRIPTION "Notification of xfp2 Ready Notify."
::= { mxpMIBNotificationPrefix 46 }

xfp2NotifyTxPower OBJECT-TYPE
	SYNTAX      Integer32
	MAX-ACCESS  read-write
	STATUS      current
	DESCRIPTION "alarm Notify"
::= { xfp2NotifyEntry 5 }

xfp2NotifyTxPowerNotification NOTIFICATION-TYPE
    OBJECTS { xfp2NotifyTxPower }
    STATUS current
    DESCRIPTION "Notification of xfp2 TxPower Notify."
::= { mxpMIBNotificationPrefix 47 }

xfp2NotifyRxPower OBJECT-TYPE
	SYNTAX      Integer32
	MAX-ACCESS  read-write
	STATUS      current
	DESCRIPTION "alarm Notify"
::= { xfp2NotifyEntry 6 }

xfp2NotifyRxPowerNotification NOTIFICATION-TYPE
    OBJECTS { xfp2NotifyRxPower }
    STATUS current
    DESCRIPTION "Notification of xfp2 Power Notify."
::= { mxpMIBNotificationPrefix 48 }

xfp2NotifyTemperature OBJECT-TYPE
	SYNTAX      Integer32
	MAX-ACCESS  read-write
	STATUS      current
	DESCRIPTION "alarm Notify"
::= { xfp2NotifyEntry 7 }

xfp2NotifyTempNotification NOTIFICATION-TYPE
    OBJECTS { xfp2NotifyTemperature }
    STATUS current
    DESCRIPTION "Notification of xfp2 Temperature Notify."
::= { mxpMIBNotificationPrefix 49 }

xfp2NotifyLowTxPower OBJECT-TYPE
	SYNTAX      Integer32
	MAX-ACCESS  read-write
	STATUS      current
	DESCRIPTION "alarm Notify"
::= { xfp2NotifyEntry 8 }

xfp2NotifyLowTxPowNotification NOTIFICATION-TYPE
    OBJECTS { xfp2NotifyLowTxPower }
    STATUS current
    DESCRIPTION "Notification of xfp2 LowTxPower Notify."
::= { mxpMIBNotificationPrefix 50 }

xfp2NotifyHighTxPower OBJECT-TYPE
	SYNTAX      Integer32
	MAX-ACCESS  read-write
	STATUS      current
	DESCRIPTION "alarm Notify"
::= { xfp2NotifyEntry 9 }

xfp2NotifyHighTxPowNotification NOTIFICATION-TYPE
    OBJECTS { xfp2NotifyHighTxPower }
    STATUS current
    DESCRIPTION "Notification of xfp2 HighTxPower Notify."
::= { mxpMIBNotificationPrefix 51 }

xfp2NotifyLowRxPower OBJECT-TYPE
	SYNTAX      Integer32
	MAX-ACCESS  read-write
	STATUS      current
	DESCRIPTION "alarm Notify"
::= { xfp2NotifyEntry 10 }

xfp2NotifyLowRxPowNotification NOTIFICATION-TYPE
    OBJECTS { xfp2NotifyLowRxPower }
    STATUS current
    DESCRIPTION "Notification of xfp2 LowRxPower Notify."
::= { mxpMIBNotificationPrefix 52 }

xfp2NotifyHighRxPower OBJECT-TYPE
	SYNTAX      Integer32
	MAX-ACCESS  read-write
	STATUS      current
	DESCRIPTION "alarm Notify"
::= { xfp2NotifyEntry 11 }

xfp2NotifyHighRxPowNotification NOTIFICATION-TYPE
    OBJECTS { xfp2NotifyHighRxPower }
    STATUS current
    DESCRIPTION "Notification of xfp2 HighRxPower Notify."
::= { mxpMIBNotificationPrefix 53 }

xfp2NotifyRxCdrLossOfLock OBJECT-TYPE
	SYNTAX      Integer32
	MAX-ACCESS  read-write
	STATUS      current
	DESCRIPTION "alarm Notify"
::= { xfp2NotifyEntry 12 }

xfp2NotifyRxCdrLOLNotification NOTIFICATION-TYPE
    OBJECTS { xfp2NotifyRxCdrLossOfLock }
    STATUS current
    DESCRIPTION "Notification of xfp2 RxCdrLossOfLock Notify."
::= { mxpMIBNotificationPrefix 54 }

xfp2NotifyTxCdrLossOfLock OBJECT-TYPE
	SYNTAX      Integer32
	MAX-ACCESS  read-write
	STATUS      current
	DESCRIPTION "alarm Notify"
::= { xfp2NotifyEntry 13 }

xfp2NotifyTxCdrLOLNotification NOTIFICATION-TYPE
    OBJECTS { xfp2NotifyTxCdrLossOfLock }
    STATUS current
    DESCRIPTION "Notification of xfp2 TxCdrLossOfLock Notify."
::= { mxpMIBNotificationPrefix 55 }

xfp2NotifyLaserFault OBJECT-TYPE
	SYNTAX      Integer32
	MAX-ACCESS  read-write
	STATUS      current
	DESCRIPTION "alarm Notify"
::= { xfp2NotifyEntry 14 }

xfp2NotifyLaserFaultNotification NOTIFICATION-TYPE
    OBJECTS { xfp2NotifyLaserFault }
    STATUS current
    DESCRIPTION "Notification of xfp2 LaserFault Notify."
::= { mxpMIBNotificationPrefix 56 }

xfp2NotifyGroup OBJECT-GROUP
    OBJECTS { xfp2NotifyPresence, xfp2NotifyRxLoss, xfp2NotifyReady, xfp2NotifyTxPower, xfp2NotifyRxPower, 
    xfp2NotifyTemperature, xfp2NotifyLowTxPower, xfp2NotifyHighTxPower, xfp2NotifyLowRxPower, 
    xfp2NotifyHighRxPower, xfp2NotifyRxCdrLossOfLock, xfp2NotifyTxCdrLossOfLock, xfp2NotifyLaserFault }
    STATUS  current
    DESCRIPTION
        "The xfp2NotifyGroup, groups objects of xfp2Notify."
    ::= { mxpNotifyGroups 4 }

xfp2NotificationGroup NOTIFICATION-GROUP
    NOTIFICATIONS { xfp2NotifyPresenceNotification, xfp2NotifyRxLossNotification, xfp2NotifyReadyNotification, xfp2NotifyTxPowerNotification, xfp2NotifyRxPowerNotification, xfp2NotifyTempNotification, xfp2NotifyLowTxPowNotification, xfp2NotifyHighTxPowNotification, xfp2NotifyLowRxPowNotification, xfp2NotifyHighRxPowNotification, xfp2NotifyRxCdrLOLNotification, xfp2NotifyTxCdrLOLNotification, xfp2NotifyLaserFaultNotification }
    STATUS  current
    DESCRIPTION "The xfp2NotificationGroup, groups notifications of xfp2."
    ::= { mxpNotificationGroups 4 }

--
-- Table for xfp3Notify
--

xfp3NotifyTable OBJECT-TYPE
	SYNTAX SEQUENCE OF XFP3NotifyEntry
	MAX-ACCESS not-accessible
	STATUS current
	DESCRIPTION "A table containing information on xfp3Notify."
::= { mxpMIBNotifyObjects 5 }

xfp3NotifyEntry OBJECT-TYPE
	SYNTAX	XFP3NotifyEntry
	MAX-ACCESS	not-accessible
	STATUS	current
	DESCRIPTION "An entry of the xfp3Notify table."
	INDEX	{ xfp3NotifyIndex }
::= { xfp3NotifyTable  1 }

XFP3NotifyEntry ::= SEQUENCE { xfp3NotifyIndex Integer32, xfp3NotifyPresence Integer32, xfp3NotifyRxLoss Integer32, xfp3NotifyReady Integer32,
 xfp3NotifyTxPower Integer32, xfp3NotifyRxPower Integer32, xfp3NotifyTemperature Integer32, xfp3NotifyLowTxPower Integer32, xfp3NotifyHighTxPower Integer32, 
 xfp3NotifyLowRxPower Integer32, xfp3NotifyHighRxPower Integer32, xfp3NotifyRxCdrLossOfLock Integer32, xfp3NotifyTxCdrLossOfLock Integer32, xfp3NotifyLaserFault Integer32}

xfp3NotifyIndex OBJECT-TYPE
	SYNTAX	Integer32 (0..65535)
	MAX-ACCESS	not-accessible
	STATUS	current
	DESCRIPTION "The auxiliary variable used for identifying instances
            of the columnar objects in the xfpTable"
::= { xfp3NotifyEntry 1 }

xfp3NotifyPresence OBJECT-TYPE
	SYNTAX      Integer32
	MAX-ACCESS  read-write
	STATUS      current
	DESCRIPTION "alarm Notify"
::= { xfp3NotifyEntry 2 }

xfp3NotifyPresenceNotification NOTIFICATION-TYPE
    OBJECTS { xfp3NotifyPresence }
    STATUS current
    DESCRIPTION "Notification of xfp3 Presence Notify."
::= { mxpMIBNotificationPrefix 57 }

xfp3NotifyRxLoss OBJECT-TYPE
	SYNTAX      Integer32
	MAX-ACCESS  read-write
	STATUS      current
	DESCRIPTION "alarm Notify"
::= { xfp3NotifyEntry 3 }

xfp3NotifyRxLossNotification NOTIFICATION-TYPE
    OBJECTS { xfp3NotifyRxLoss }
    STATUS current
    DESCRIPTION "Notification of xfp3 RxLoss Notify."
::= { mxpMIBNotificationPrefix 58 }

xfp3NotifyReady OBJECT-TYPE
	SYNTAX      Integer32
	MAX-ACCESS  read-write
	STATUS      current
	DESCRIPTION "alarm Notify"
::= { xfp3NotifyEntry 4 }

xfp3NotifyReadyNotification NOTIFICATION-TYPE
    OBJECTS { xfp3NotifyReady }
    STATUS current
    DESCRIPTION "Notification of xfp3 Ready Notify."
::= { mxpMIBNotificationPrefix 59 }

xfp3NotifyTxPower OBJECT-TYPE
	SYNTAX      Integer32
	MAX-ACCESS  read-write
	STATUS      current
	DESCRIPTION "alarm Notify"
::= { xfp3NotifyEntry 5 }

xfp3NotifyTxPowerNotification NOTIFICATION-TYPE
    OBJECTS { xfp3NotifyTxPower }
    STATUS current
    DESCRIPTION "Notification of xfp3 TxPower Notify."
::= { mxpMIBNotificationPrefix 60 }

xfp3NotifyRxPower OBJECT-TYPE
	SYNTAX      Integer32
	MAX-ACCESS  read-write
	STATUS      current
	DESCRIPTION "alarm Notify"
::= { xfp3NotifyEntry 6 }

xfp3NotifyRxPowerNotification NOTIFICATION-TYPE
    OBJECTS { xfp3NotifyRxPower }
    STATUS current
    DESCRIPTION "Notification of xfp3 Power Notify."
::= { mxpMIBNotificationPrefix 61 }

xfp3NotifyTemperature OBJECT-TYPE
	SYNTAX      Integer32
	MAX-ACCESS  read-write
	STATUS      current
	DESCRIPTION "alarm Notify"
::= { xfp3NotifyEntry 7 }

xfp3NotifyTempNotification NOTIFICATION-TYPE
    OBJECTS { xfp3NotifyTemperature }
    STATUS current
    DESCRIPTION "Notification of xfp3 Temperature Notify."
::= { mxpMIBNotificationPrefix 62 }

xfp3NotifyLowTxPower OBJECT-TYPE
	SYNTAX      Integer32
	MAX-ACCESS  read-write
	STATUS      current
	DESCRIPTION "alarm Notify"
::= { xfp3NotifyEntry 8 }

xfp3NotifyLowTxPowNotification NOTIFICATION-TYPE
    OBJECTS { xfp3NotifyLowTxPower }
    STATUS current
    DESCRIPTION "Notification of xfp3 LowTxPower Notify."
::= { mxpMIBNotificationPrefix 63 }

xfp3NotifyHighTxPower OBJECT-TYPE
	SYNTAX      Integer32
	MAX-ACCESS  read-write
	STATUS      current
	DESCRIPTION "alarm Notify"
::= { xfp3NotifyEntry 9 }

xfp3NotifyHighTxPowNotification NOTIFICATION-TYPE
    OBJECTS { xfp3NotifyHighTxPower }
    STATUS current
    DESCRIPTION "Notification of xfp3 HighTxPower Notify."
::= { mxpMIBNotificationPrefix 64 }

xfp3NotifyLowRxPower OBJECT-TYPE
	SYNTAX      Integer32
	MAX-ACCESS  read-write
	STATUS      current
	DESCRIPTION "alarm Notify"
::= { xfp3NotifyEntry 10 }

xfp3NotifyLowRxPowNotification NOTIFICATION-TYPE
    OBJECTS { xfp3NotifyLowRxPower }
    STATUS current
    DESCRIPTION "Notification of xfp3 LowRxPower Notify."
::= { mxpMIBNotificationPrefix 65 }

xfp3NotifyHighRxPower OBJECT-TYPE
	SYNTAX      Integer32
	MAX-ACCESS  read-write
	STATUS      current
	DESCRIPTION "alarm Notify"
::= { xfp3NotifyEntry 11 }

xfp3NotifyHighRxPowNotification NOTIFICATION-TYPE
    OBJECTS { xfp3NotifyHighRxPower }
    STATUS current
    DESCRIPTION "Notification of xfp3 HighRxPower Notify."
::= { mxpMIBNotificationPrefix 66 }

xfp3NotifyRxCdrLossOfLock OBJECT-TYPE
	SYNTAX      Integer32
	MAX-ACCESS  read-write
	STATUS      current
	DESCRIPTION "alarm Notify"
::= { xfp3NotifyEntry 12 }

xfp3NotifyRxCdrLOLNotification NOTIFICATION-TYPE
    OBJECTS { xfp3NotifyRxCdrLossOfLock }
    STATUS current
    DESCRIPTION "Notification of xfp3 RxCdrLossOfLock Notify."
::= { mxpMIBNotificationPrefix 67 }

xfp3NotifyTxCdrLossOfLock OBJECT-TYPE
	SYNTAX      Integer32
	MAX-ACCESS  read-write
	STATUS      current
	DESCRIPTION "alarm Notify"
::= { xfp3NotifyEntry 13 }

xfp3NotifyTxCdrLOLNotification NOTIFICATION-TYPE
    OBJECTS { xfp3NotifyTxCdrLossOfLock }
    STATUS current
    DESCRIPTION "Notification of xfp3 TxCdrLossOfLock Notify."
::= { mxpMIBNotificationPrefix 68 }

xfp3NotifyLaserFault OBJECT-TYPE
	SYNTAX      Integer32
	MAX-ACCESS  read-write
	STATUS      current
	DESCRIPTION "alarm Notify"
::= { xfp3NotifyEntry 14 }

xfp3NotifyLaserFaultNotification NOTIFICATION-TYPE
    OBJECTS { xfp3NotifyLaserFault }
    STATUS current
    DESCRIPTION "Notification of xfp3 LaserFault Notify."
::= { mxpMIBNotificationPrefix 69 }

xfp3NotifyGroup OBJECT-GROUP
    OBJECTS { xfp3NotifyPresence, xfp3NotifyRxLoss, xfp3NotifyReady, xfp3NotifyTxPower, xfp3NotifyRxPower, 
    xfp3NotifyTemperature, xfp3NotifyLowTxPower, xfp3NotifyHighTxPower, xfp3NotifyLowRxPower, 
    xfp3NotifyHighRxPower, xfp3NotifyRxCdrLossOfLock, xfp3NotifyTxCdrLossOfLock, xfp3NotifyLaserFault }
    STATUS  current
    DESCRIPTION
        "The xfp3NotifyGroup, groups objects of xfp3Notify."
    ::= { mxpNotifyGroups 5 }

xfp3NotificationGroup NOTIFICATION-GROUP
    NOTIFICATIONS { xfp3NotifyPresenceNotification, xfp3NotifyRxLossNotification, xfp3NotifyReadyNotification, xfp3NotifyTxPowerNotification, xfp3NotifyRxPowerNotification, xfp3NotifyTempNotification, xfp3NotifyLowTxPowNotification, xfp3NotifyHighTxPowNotification, xfp3NotifyLowRxPowNotification, xfp3NotifyHighRxPowNotification, xfp3NotifyRxCdrLOLNotification, xfp3NotifyTxCdrLOLNotification, xfp3NotifyLaserFaultNotification }
    STATUS  current
    DESCRIPTION "The xfp3NotificationGroup, groups notifications of xfp3."
    ::= { mxpNotificationGroups 5 }

--
-- Table for xfp4Notify
--

xfp4NotifyTable OBJECT-TYPE
	SYNTAX SEQUENCE OF XFP4NotifyEntry
	MAX-ACCESS not-accessible
	STATUS current
	DESCRIPTION "A table containing information on xfp4Notify."
::= { mxpMIBNotifyObjects 6 }

xfp4NotifyEntry OBJECT-TYPE
	SYNTAX	XFP4NotifyEntry
	MAX-ACCESS	not-accessible
	STATUS	current
	DESCRIPTION "An entry of the xfp4Notify table."
	INDEX	{ xfp4NotifyIndex }
::= { xfp4NotifyTable  1 }

XFP4NotifyEntry ::= SEQUENCE { xfp4NotifyIndex Integer32, xfp4NotifyPresence Integer32, xfp4NotifyRxLoss Integer32, xfp4NotifyReady Integer32,
 xfp4NotifyTxPower Integer32, xfp4NotifyRxPower Integer32, xfp4NotifyTemperature Integer32, xfp4NotifyLowTxPower Integer32, xfp4NotifyHighTxPower Integer32, 
 xfp4NotifyLowRxPower Integer32, xfp4NotifyHighRxPower Integer32, xfp4NotifyRxCdrLossOfLock Integer32, xfp4NotifyTxCdrLossOfLock Integer32, xfp4NotifyLaserFault Integer32}

xfp4NotifyIndex OBJECT-TYPE
	SYNTAX	Integer32 (0..65535)
	MAX-ACCESS	not-accessible
	STATUS	current
	DESCRIPTION "The auxiliary variable used for identifying instances
            of the columnar objects in the xfpTable"
::= { xfp4NotifyEntry 1 }

xfp4NotifyPresence OBJECT-TYPE
	SYNTAX      Integer32
	MAX-ACCESS  read-write
	STATUS      current
	DESCRIPTION "alarm Notify"
::= { xfp4NotifyEntry 2 }

xfp4NotifyPresenceNotification NOTIFICATION-TYPE
    OBJECTS { xfp4NotifyPresence }
    STATUS current
    DESCRIPTION "Notification of xfp4 Presence Notify."
::= { mxpMIBNotificationPrefix 70 }

xfp4NotifyRxLoss OBJECT-TYPE
	SYNTAX      Integer32
	MAX-ACCESS  read-write
	STATUS      current
	DESCRIPTION "alarm Notify"
::= { xfp4NotifyEntry 3 }

xfp4NotifyRxLossNotification NOTIFICATION-TYPE
    OBJECTS { xfp4NotifyRxLoss }
    STATUS current
    DESCRIPTION "Notification of xfp4 RxLoss Notify."
::= { mxpMIBNotificationPrefix 71 }

xfp4NotifyReady OBJECT-TYPE
	SYNTAX      Integer32
	MAX-ACCESS  read-write
	STATUS      current
	DESCRIPTION "alarm Notify"
::= { xfp4NotifyEntry 4 }

xfp4NotifyReadyNotification NOTIFICATION-TYPE
    OBJECTS { xfp4NotifyReady }
    STATUS current
    DESCRIPTION "Notification of xfp4 Ready Notify."
::= { mxpMIBNotificationPrefix 72 }

xfp4NotifyTxPower OBJECT-TYPE
	SYNTAX      Integer32
	MAX-ACCESS  read-write
	STATUS      current
	DESCRIPTION "alarm Notify"
::= { xfp4NotifyEntry 5 }

xfp4NotifyTxPowerNotification NOTIFICATION-TYPE
    OBJECTS { xfp4NotifyTxPower }
    STATUS current
    DESCRIPTION "Notification of xfp4 TxPower Notify."
::= { mxpMIBNotificationPrefix 73 }

xfp4NotifyRxPower OBJECT-TYPE
	SYNTAX      Integer32
	MAX-ACCESS  read-write
	STATUS      current
	DESCRIPTION "alarm Notify"
::= { xfp4NotifyEntry 6 }

xfp4NotifyRxPowerNotification NOTIFICATION-TYPE
    OBJECTS { xfp4NotifyRxPower }
    STATUS current
    DESCRIPTION "Notification of xfp4 Power Notify."
::= { mxpMIBNotificationPrefix 74 }

xfp4NotifyTemperature OBJECT-TYPE
	SYNTAX      Integer32
	MAX-ACCESS  read-write
	STATUS      current
	DESCRIPTION "alarm Notify"
::= { xfp4NotifyEntry 7 }

xfp4NotifyTempNotification NOTIFICATION-TYPE
    OBJECTS { xfp4NotifyTemperature }
    STATUS current
    DESCRIPTION "Notification of xfp4 Temperature Notify."
::= { mxpMIBNotificationPrefix 75 }

xfp4NotifyLowTxPower OBJECT-TYPE
	SYNTAX      Integer32
	MAX-ACCESS  read-write
	STATUS      current
	DESCRIPTION "alarm Notify"
::= { xfp4NotifyEntry 8 }

xfp4NotifyLowTxPowNotification NOTIFICATION-TYPE
    OBJECTS { xfp4NotifyLowTxPower }
    STATUS current
    DESCRIPTION "Notification of xfp4 LowTxPower Notify."
::= { mxpMIBNotificationPrefix 76 }

xfp4NotifyHighTxPower OBJECT-TYPE
	SYNTAX      Integer32
	MAX-ACCESS  read-write
	STATUS      current
	DESCRIPTION "alarm Notify"
::= { xfp4NotifyEntry 9 }

xfp4NotifyHighTxPowNotification NOTIFICATION-TYPE
    OBJECTS { xfp4NotifyHighTxPower }
    STATUS current
    DESCRIPTION "Notification of xfp4 HighTxPower Notify."
::= { mxpMIBNotificationPrefix 77 }

xfp4NotifyLowRxPower OBJECT-TYPE
	SYNTAX      Integer32
	MAX-ACCESS  read-write
	STATUS      current
	DESCRIPTION "alarm Notify"
::= { xfp4NotifyEntry 10 }

xfp4NotifyLowRxPowNotification NOTIFICATION-TYPE
    OBJECTS { xfp4NotifyLowRxPower }
    STATUS current
    DESCRIPTION "Notification of xfp4 LowRxPower Notify."
::= { mxpMIBNotificationPrefix 78 }

xfp4NotifyHighRxPower OBJECT-TYPE
	SYNTAX      Integer32
	MAX-ACCESS  read-write
	STATUS      current
	DESCRIPTION "alarm Notify"
::= { xfp4NotifyEntry 11 }

xfp4NotifyHighRxPowNotification NOTIFICATION-TYPE
    OBJECTS { xfp4NotifyHighRxPower }
    STATUS current
    DESCRIPTION "Notification of xfp4 HighRxPower Notify."
::= { mxpMIBNotificationPrefix 79 }

xfp4NotifyRxCdrLossOfLock OBJECT-TYPE
	SYNTAX      Integer32
	MAX-ACCESS  read-write
	STATUS      current
	DESCRIPTION "alarm Notify"
::= { xfp4NotifyEntry 12 }

xfp4NotifyRxCdrLOLNotification NOTIFICATION-TYPE
    OBJECTS { xfp4NotifyRxCdrLossOfLock }
    STATUS current
    DESCRIPTION "Notification of xfp4 RxCdrLossOfLock Notify."
::= { mxpMIBNotificationPrefix 80 }

xfp4NotifyTxCdrLossOfLock OBJECT-TYPE
	SYNTAX      Integer32
	MAX-ACCESS  read-write
	STATUS      current
	DESCRIPTION "alarm Notify"
::= { xfp4NotifyEntry 13 }

xfp4NotifyTxCdrLOLNotification NOTIFICATION-TYPE
    OBJECTS { xfp4NotifyTxCdrLossOfLock }
    STATUS current
    DESCRIPTION "Notification of xfp4 TxCdrLossOfLock Notify."
::= { mxpMIBNotificationPrefix 81 }

xfp4NotifyLaserFault OBJECT-TYPE
	SYNTAX      Integer32
	MAX-ACCESS  read-write
	STATUS      current
	DESCRIPTION "alarm Notify"
::= { xfp4NotifyEntry 14 }

xfp4NotifyLaserFaultNotification NOTIFICATION-TYPE
    OBJECTS { xfp4NotifyLaserFault }
    STATUS current
    DESCRIPTION "Notification of xfp4 LaserFault Notify."
::= { mxpMIBNotificationPrefix 82 }

xfp4NotifyGroup OBJECT-GROUP
    OBJECTS { xfp4NotifyPresence, xfp4NotifyRxLoss, xfp4NotifyReady, xfp4NotifyTxPower, xfp4NotifyRxPower, 
    xfp4NotifyTemperature, xfp4NotifyLowTxPower, xfp4NotifyHighTxPower, xfp4NotifyLowRxPower, 
    xfp4NotifyHighRxPower, xfp4NotifyRxCdrLossOfLock, xfp4NotifyTxCdrLossOfLock, xfp4NotifyLaserFault }
    STATUS  current
    DESCRIPTION
        "The xfp4NotifyGroup, groups objects of xfp4Notify."
    ::= { mxpNotifyGroups 6 }

xfp4NotificationGroup NOTIFICATION-GROUP
    NOTIFICATIONS { xfp4NotifyPresenceNotification, xfp4NotifyRxLossNotification, xfp4NotifyReadyNotification, xfp4NotifyTxPowerNotification, xfp4NotifyRxPowerNotification, xfp4NotifyTempNotification, xfp4NotifyLowTxPowNotification, xfp4NotifyHighTxPowNotification, xfp4NotifyLowRxPowNotification, xfp4NotifyHighRxPowNotification, xfp4NotifyRxCdrLOLNotification, xfp4NotifyTxCdrLOLNotification, xfp4NotifyLaserFaultNotification }
    STATUS  current
    DESCRIPTION "The xfp4NotificationGroup, groups notifications of xfp4."
    ::= { mxpNotificationGroups 6 }


--
-- Table for Traffic Processor
--

tpNotifyTable OBJECT-TYPE
	SYNTAX SEQUENCE OF TpNotifyEntry
	MAX-ACCESS not-accessible
	STATUS current
	DESCRIPTION "A table containing notifications for Traffic Processor."
::= { mxpMIBNotifyObjects 7 }

tpNotifyEntry OBJECT-TYPE
	SYNTAX	TpNotifyEntry
	MAX-ACCESS	not-accessible
	STATUS	current
	DESCRIPTION "An entry of the tpNotify table."
	INDEX	{ tpNotifyIndex }
::= { tpNotifyTable  1 }

TpNotifyEntry ::= SEQUENCE { tpNotifyIndex Integer32, tpNotifyLineFramerFsmmtrb3s Integer32, tpNotifyLineFramerFsmmtrb2s Integer32, tpNotifyLineFramerFsmmtrb1s Integer32, tpNotifyLineFramerFsmms Integer32, tpNotifyLineFramerSif Integer32, tpNotifyLineFramerSoof Integer32, tpNotifyLineFramerSlof Integer32, tpNotifyLineFramerFst Integer32, tpNotifyLineLosstatLosf Integer32, tpNotifyLineSecmonFlom Integer32, tpNotifyLineSecmonBipsfs Integer32, tpNotifyLineSecmonDiae Integer32, tpNotifyLineSecmonDbdi Integer32, tpNotifyLineSecmonLom Integer32, tpNotifyLinePathmonAccstat Integer32, tpNotifyLinePathmonMsiunst Integer32, tpNotifyLinePathmonDais Integer32, tpNotifyLinePathmonDlck Integer32, tpNotifyLinePathmonDbdi Integer32, tpNotifyClient1FramerFsmms Integer32, tpNotifyClient1FramerFsusts Integer32, tpNotifyClient1FramerSif Integer32, tpNotifyClient1FramerSoof Integer32, tpNotifyClient1FramerSlof Integer32, tpNotifyClient1FramerFst Integer32, tpNotifyClient1LosstatLosf Integer32, tpNotifyClient1SecmonFlom Integer32, tpNotifyClient1SecmonBipsfs Integer32, tpNotifyClient1SecmonDiae Integer32, tpNotifyClient1SecmonDbdi Integer32, tpNotifyClient1SecmonLom Integer32, tpNotifyClient1PathmonAccstat Integer32, tpNotifyClient1PathmonMsiunst Integer32, tpNotifyClient1PathmonDais Integer32, tpNotifyClient1PathmonDlck Integer32, tpNotifyClient1PathmonDbdi Integer32, tpNotifyClient2FramerFsmms Integer32, tpNotifyClient2FramerFsusts Integer32, tpNotifyClient2FramerSif Integer32, tpNotifyClient2FramerSoof Integer32, tpNotifyClient2FramerSlof Integer32, tpNotifyClient2FramerFst Integer32, tpNotifyClient2LosstatLosf Integer32, tpNotifyClient2SecmonFlom Integer32, tpNotifyClient2SecmonBipsfs Integer32, tpNotifyClient2SecmonDiae Integer32, tpNotifyClient2SecmonDbdi Integer32, tpNotifyClient2SecmonLom Integer32, tpNotifyClient2PathmonAccstat Integer32, tpNotifyClient2PathmonMsiunst Integer32, tpNotifyClient2PathmonDais Integer32, tpNotifyClient2PathmonDlck Integer32, tpNotifyClient2PathmonDbdi Integer32, tpNotifyClient3FramerFsmms Integer32, tpNotifyClient3FramerFsusts Integer32, tpNotifyClient3FramerSif Integer32, tpNotifyClient3FramerSoof Integer32, tpNotifyClient3FramerSlof Integer32, tpNotifyClient3FramerFst Integer32, tpNotifyClient3LosstatLosf Integer32, tpNotifyClient3SecmonFlom Integer32, tpNotifyClient3SecmonBipsfs Integer32, tpNotifyClient3SecmonDiae Integer32, tpNotifyClient3SecmonDbdi Integer32, tpNotifyClient3SecmonLom Integer32, tpNotifyClient3PathmonAccstat Integer32, tpNotifyClient3PathmonMsiunst Integer32, tpNotifyClient3PathmonDais Integer32, tpNotifyClient3PathmonDlck Integer32, tpNotifyClient3PathmonDbdi Integer32, tpNotifyClient4FramerFsmms Integer32, tpNotifyClient4FramerFsusts Integer32, tpNotifyClient4FramerSif Integer32, tpNotifyClient4FramerSoof Integer32, tpNotifyClient4FramerSlof Integer32, tpNotifyClient4FramerFst Integer32, tpNotifyClient4LosstatLosf Integer32, tpNotifyClient4SecmonFlom Integer32, tpNotifyClient4SecmonBipsfs Integer32, tpNotifyClient4SecmonDiae Integer32, tpNotifyClient4SecmonDbdi Integer32, tpNotifyClient4SecmonLom Integer32, tpNotifyClient4PathmonAccstat Integer32, tpNotifyClient4PathmonMsiunst Integer32, tpNotifyClient4PathmonDais Integer32, tpNotifyClient4PathmonDlck Integer32, tpNotifyClient4PathmonDbdi Integer32 }

tpNotifyIndex OBJECT-TYPE
	SYNTAX	Integer32 (0..65535)
	MAX-ACCESS	not-accessible
	STATUS	current
	DESCRIPTION "The auxiliary variable used for identifying instances
            of the columnar objects in the tpTable"
::= { tpNotifyEntry 1 }

tpNotifyLineFramerFsmmtrb3s OBJECT-TYPE
	SYNTAX      Integer32
	MAX-ACCESS  read-write
	STATUS      current
	DESCRIPTION "lineFramerFsmmtrb3s Notify"
::= { tpNotifyEntry 2 }

tpNotifyLineFramerFsmmtrb3sNotification NOTIFICATION-TYPE
    OBJECTS { tpNotifyLineFramerFsmmtrb3s }
    STATUS current
    DESCRIPTION "Notification of tpNotifyLineFramerFsmmtrb3s."
::= { mxpMIBNotificationPrefix 83 }

tpNotifyLineFramerFsmmtrb2s OBJECT-TYPE
	SYNTAX      Integer32
	MAX-ACCESS  read-write
	STATUS      current
	DESCRIPTION "lineFsmmtrb2s Notify"
::= { tpNotifyEntry 3 }

tpNotifyLineFramerFsmmtrb2sNotification NOTIFICATION-TYPE
    OBJECTS { tpNotifyLineFramerFsmmtrb2s }
    STATUS current
    DESCRIPTION "Notification of tpNotifyLineFramerFsmmtrb2s."
::= { mxpMIBNotificationPrefix 84 }

tpNotifyLineFramerFsmmtrb1s OBJECT-TYPE
	SYNTAX      Integer32
	MAX-ACCESS  read-write
	STATUS      current
	DESCRIPTION "lineFramerFsmmtrb1s Notify"
::= { tpNotifyEntry 4 }

tpNotifyLineFramerFsmmtrb1sNotification NOTIFICATION-TYPE
    OBJECTS { tpNotifyLineFramerFsmmtrb1s }
    STATUS current
    DESCRIPTION "Notification of tpNotifyLineFramerFsmmtrb1s."
::= { mxpMIBNotificationPrefix 85 }

tpNotifyLineFramerFsmms OBJECT-TYPE
	SYNTAX      Integer32
	MAX-ACCESS  read-write
	STATUS      current
	DESCRIPTION "lineFramerFsmms Notify"
::= { tpNotifyEntry 5 }

tpNotifyLineFramerFsmmsNotification NOTIFICATION-TYPE
    OBJECTS { tpNotifyLineFramerFsmms }
    STATUS current
    DESCRIPTION "Notification of tpNotifyLineFramerFsmms."
::= { mxpMIBNotificationPrefix 86 }

tpNotifyLineFramerSif OBJECT-TYPE
	SYNTAX      Integer32
	MAX-ACCESS  read-write
	STATUS      current
	DESCRIPTION "lineFramerSif Notify"
::= { tpNotifyEntry 6 }

tpNotifyLineFramerSifNotification NOTIFICATION-TYPE
    OBJECTS { tpNotifyLineFramerSif }
    STATUS current
    DESCRIPTION "Notification of tpNotifyLineFramerSif."
::= { mxpMIBNotificationPrefix 87 }

tpNotifyLineFramerSoof OBJECT-TYPE
	SYNTAX      Integer32
	MAX-ACCESS  read-write
	STATUS      current
	DESCRIPTION "lineFramerSoof Notify"
::= { tpNotifyEntry 7 }

tpNotifyLineFramerSoofNotification NOTIFICATION-TYPE
    OBJECTS { tpNotifyLineFramerSoof }
    STATUS current
    DESCRIPTION "Notification of tpNotifyLineFramerSoof."
::= { mxpMIBNotificationPrefix 88 }

tpNotifyLineFramerSlof OBJECT-TYPE
	SYNTAX      Integer32
	MAX-ACCESS  read-write
	STATUS      current
	DESCRIPTION "lineFramerSlof Notify"
::= { tpNotifyEntry 8 }

tpNotifyLineFramerSlofNotification NOTIFICATION-TYPE
    OBJECTS { lineFramerSlof }
    STATUS current
    DESCRIPTION "Notification of tpNotifyLineFramerSlof."
::= { mxpMIBNotificationPrefix 89 }

tpNotifyLineFramerFst OBJECT-TYPE
	SYNTAX      Integer32
	MAX-ACCESS  read-write
	STATUS      current
	DESCRIPTION "lineFramerFst Notify"
::= { tpNotifyEntry 9 }

tpNotifyLineFramerFstNotification NOTIFICATION-TYPE
    OBJECTS { tpNotifyLineFramerFst }
    STATUS current
    DESCRIPTION "Notification of tpNotifyLineFramerFst."
::= { mxpMIBNotificationPrefix 90 }

tpNotifyLineLosstatLosf OBJECT-TYPE
	SYNTAX      Integer32
	MAX-ACCESS  read-write
	STATUS      current
	DESCRIPTION "lineLosstatLosf Notify"
::= { tpNotifyEntry 10 }

tpNotifyLineLosstatLosfNotification NOTIFICATION-TYPE
    OBJECTS { tpNotifyLineLosstatLosf }
    STATUS current
    DESCRIPTION "Notification of tpNotifyLineLosstatLosf."
::= { mxpMIBNotificationPrefix 91 }

tpNotifyLineSecmonFlom OBJECT-TYPE
	SYNTAX      Integer32
	MAX-ACCESS  read-write
	STATUS      current
	DESCRIPTION "lineSecmonFlom Notify"
::= { tpNotifyEntry 11 }

tpNotifyLineSecmonFlomNotification NOTIFICATION-TYPE
    OBJECTS { tpNotifyLineSecmonFlom }
    STATUS current
    DESCRIPTION "Notification of tpNotifyLineSecmonFlom."
::= { mxpMIBNotificationPrefix 92 }

tpNotifyLineSecmonBipsfs OBJECT-TYPE
	SYNTAX      Integer32
	MAX-ACCESS  read-write
	STATUS      current
	DESCRIPTION "lineSecmonBipsfs Notify"
::= { tpNotifyEntry 12 }

tpNotifyLineSecmonBipsfsNotification NOTIFICATION-TYPE
    OBJECTS { tpNotifyLineSecmonBipsfs }
    STATUS current
    DESCRIPTION "Notification of tpNotifyLineSecmonBipsfs."
::= { mxpMIBNotificationPrefix 93 }

tpNotifyLineSecmonDiae OBJECT-TYPE
	SYNTAX      Integer32
	MAX-ACCESS  read-write
	STATUS      current
	DESCRIPTION "lineSecmonDiae Notify"
::= { tpNotifyEntry 13 }

tpNotifyLineSecmonDiaeNotification NOTIFICATION-TYPE
    OBJECTS { tpNotifyLineSecmonDiae }
    STATUS current
    DESCRIPTION "Notification of tpNotifyLineSecmonDiae."
::= { mxpMIBNotificationPrefix 94 }

tpNotifyLineSecmonDbdi OBJECT-TYPE
	SYNTAX      Integer32
	MAX-ACCESS  read-write
	STATUS      current
	DESCRIPTION "lineSecmonDbdi Notify"
::= { tpNotifyEntry 14 }

tpNotifyLineSecmonDbdiNotification NOTIFICATION-TYPE
    OBJECTS { tpNotifyLineSecmonDbdi }
    STATUS current
    DESCRIPTION "Notification of tpNotifyLineSecmonDbdi."
::= { mxpMIBNotificationPrefix 95 }

tpNotifyLineSecmonLom OBJECT-TYPE
	SYNTAX      Integer32
	MAX-ACCESS  read-write
	STATUS      current
	DESCRIPTION "lineSecmonLom Notify"
::= { tpNotifyEntry 15 }

tpNotifyLineSecmonLomNotification NOTIFICATION-TYPE
    OBJECTS { tpNotifyLineSecmonLom }
    STATUS current
    DESCRIPTION "Notification of tpNotifyLineSecmonLom."
::= { mxpMIBNotificationPrefix 96 }

tpNotifyLinePathmonAccstat OBJECT-TYPE
	SYNTAX      Integer32
	MAX-ACCESS  read-write
	STATUS      current
	DESCRIPTION "linePathmonAccstat Notify"
::= { tpNotifyEntry 16 }

tpNotifyLinePathmonAccstatNotification NOTIFICATION-TYPE
    OBJECTS { tpNotifyLinePathmonAccstat }
    STATUS current
    DESCRIPTION "Notification of tpNotifyLinePathmonAccstat."
::= { mxpMIBNotificationPrefix 97 }

tpNotifyLinePathmonMsiunst OBJECT-TYPE
	SYNTAX      Integer32
	MAX-ACCESS  read-write
	STATUS      current
	DESCRIPTION "linePathmonMsiunst Notify"
::= { tpNotifyEntry 17 }

tpNotifyLinePathmonMsiunstNotification NOTIFICATION-TYPE
    OBJECTS { tpNotifyLinePathmonMsiunst }
    STATUS current
    DESCRIPTION "Notification of tpNotifyLinePathmonMsiunst."
::= { mxpMIBNotificationPrefix 98 }

tpNotifyLinePathmonDais OBJECT-TYPE
	SYNTAX      Integer32
	MAX-ACCESS  read-write
	STATUS      current
	DESCRIPTION "linePathmonDais Notify"
::= { tpNotifyEntry 18 }

tpNotifyLinePathmonDaisNotification NOTIFICATION-TYPE
    OBJECTS { tpNotifyLinePathmonDais }
    STATUS current
    DESCRIPTION "Notification of tpNotifyLinePathmonDais."
::= { mxpMIBNotificationPrefix 99 }

tpNotifyLinePathmonDlck OBJECT-TYPE
	SYNTAX      Integer32
	MAX-ACCESS  read-write
	STATUS      current
	DESCRIPTION "linePathmonDlck Notify"
::= { tpNotifyEntry 19 }

tpNotifyLinePathmonDlckNotification NOTIFICATION-TYPE
    OBJECTS { tpNotifyLinePathmonDlck }
    STATUS current
    DESCRIPTION "Notification of tpNotifyLinePathmonDlck."
::= { mxpMIBNotificationPrefix 100 }

tpNotifyLinePathmonDbdi OBJECT-TYPE
	SYNTAX      Integer32
	MAX-ACCESS  read-write
	STATUS      current
	DESCRIPTION "linePathmonDbdi Notify"
::= { tpNotifyEntry 20 }

tpNotifyLinePathmonDbdiNotification NOTIFICATION-TYPE
    OBJECTS { tpNotifyLinePathmonDbdi }
    STATUS current
    DESCRIPTION "Notification of tpNotifyLinePathmonDbdi."
::= { mxpMIBNotificationPrefix 101 }

tpNotifyClient1FramerFsmms OBJECT-TYPE
	SYNTAX      Integer32
	MAX-ACCESS  read-write
	STATUS      current
	DESCRIPTION "client1FramerFsmms Notify"
::= { tpNotifyEntry 21 }

tpNotifyClient1FramerFsmmsNotification NOTIFICATION-TYPE
    OBJECTS { tpNotifyClient1FramerFsmms }
    STATUS current
    DESCRIPTION "Notification of tpNotifyClient1FramerFsmms."
::= { mxpMIBNotificationPrefix 102 }

tpNotifyClient1FramerFsusts OBJECT-TYPE
	SYNTAX      Integer32
	MAX-ACCESS  read-write
	STATUS      current
	DESCRIPTION "client1FramerFsusts Notify"
::= { tpNotifyEntry 22 }

tpNotifyClient1FramerFsustsNotification NOTIFICATION-TYPE
    OBJECTS { tpNotifyClient1FramerFsusts }
    STATUS current
    DESCRIPTION "Notification of tpNotifyClient1FramerFsusts."
::= { mxpMIBNotificationPrefix 103 }

tpNotifyClient1FramerSif OBJECT-TYPE
	SYNTAX      Integer32
	MAX-ACCESS  read-write
	STATUS      current
	DESCRIPTION "client1FramerSif Notify"
::= { tpNotifyEntry 23 }

tpNotifyClient1FramerSifNotification NOTIFICATION-TYPE
    OBJECTS { tpNotifyClient1FramerSif }
    STATUS current
    DESCRIPTION "Notification of tpNotifyClient1FramerSif."
::= { mxpMIBNotificationPrefix 104 }

tpNotifyClient1FramerSoof OBJECT-TYPE
	SYNTAX      Integer32
	MAX-ACCESS  read-write
	STATUS      current
	DESCRIPTION "client1FramerSoof Notify"
::= { tpNotifyEntry 24 }

tpNotifyClient1FramerSoofNotification NOTIFICATION-TYPE
    OBJECTS { tpNotifyClient1FramerSoof }
    STATUS current
    DESCRIPTION "Notification of tpNotifyClient1FramerSoof."
::= { mxpMIBNotificationPrefix 105 }

tpNotifyClient1FramerSlof OBJECT-TYPE
	SYNTAX      Integer32
	MAX-ACCESS  read-write
	STATUS      current
	DESCRIPTION "client1FramerSlof Notify"
::= { tpNotifyEntry 25 }

tpNotifyClient1FramerSlofNotification NOTIFICATION-TYPE
    OBJECTS { tpNotifyClient1FramerSlof }
    STATUS current
    DESCRIPTION "Notification of tpNotifyClient1FramerSoof."
::= { mxpMIBNotificationPrefix 106 }

tpNotifyClient1FramerFst OBJECT-TYPE
	SYNTAX      Integer32
	MAX-ACCESS  read-write
	STATUS      current
	DESCRIPTION "client1FramerFst Notify"
::= { tpNotifyEntry 26 }

tpNotifyClient1FramerFstNotification NOTIFICATION-TYPE
    OBJECTS { tpNotifyClient1FramerFst }
    STATUS current
    DESCRIPTION "Notification of tpNotifyClient1FramerFst."
::= { mxpMIBNotificationPrefix 107 }

tpNotifyClient1LosstatLosf OBJECT-TYPE
	SYNTAX      Integer32
	MAX-ACCESS  read-write
	STATUS      current
	DESCRIPTION "client1LosstatLosf Notify"
::= { tpNotifyEntry 27 }

tpNotifyClient1LosstatLosfNotification NOTIFICATION-TYPE
    OBJECTS { tpNotifyClient1LosstatLosf }
    STATUS current
    DESCRIPTION "Notification of tpNotifyClient1LosstatLosf."
::= { mxpMIBNotificationPrefix 108 }

tpNotifyClient1SecmonFlom OBJECT-TYPE
	SYNTAX      Integer32
	MAX-ACCESS  read-write
	STATUS      current
	DESCRIPTION "client1SecmonFlom Notify"
::= { tpNotifyEntry 28 }

tpNotifyClient1SecmonFlomNotification NOTIFICATION-TYPE
    OBJECTS { tpNotifyClient1SecmonFlom }
    STATUS current
    DESCRIPTION "Notification of tpNotifyClient1SecmonFlom."
::= { mxpMIBNotificationPrefix 109 }

tpNotifyClient1SecmonBipsfs OBJECT-TYPE
	SYNTAX      Integer32
	MAX-ACCESS  read-write
	STATUS      current
	DESCRIPTION "client1SecmonBipsfs Notify"
::= { tpNotifyEntry 29 }

tpNotifyClient1SecmonBipsfsNotification NOTIFICATION-TYPE
    OBJECTS { tpNotifyClient1SecmonBipsfs }
    STATUS current
    DESCRIPTION "Notification of tpNotifyClient1SecmonBipsfs."
::= { mxpMIBNotificationPrefix 110 }

tpNotifyClient1SecmonDiae OBJECT-TYPE
	SYNTAX      Integer32
	MAX-ACCESS  read-write
	STATUS      current
	DESCRIPTION "client1SecmonDiae Notify"
::= { tpNotifyEntry 30 }

tpNotifyClient1SecmonDiaeNotification NOTIFICATION-TYPE
    OBJECTS { tpNotifyClient1SecmonDiae }
    STATUS current
    DESCRIPTION "Notification of tpNotifyClient1SecmonDiae."
::= { mxpMIBNotificationPrefix 111 }

tpNotifyClient1SecmonDbdi OBJECT-TYPE
	SYNTAX      Integer32
	MAX-ACCESS  read-write
	STATUS      current
	DESCRIPTION "client1SecmonDbdi Notify"
::= { tpNotifyEntry 31 }

tpNotifyClient1SecmonDbdiNotification NOTIFICATION-TYPE
    OBJECTS { tpNotifyClient1SecmonDbdi }
    STATUS current
    DESCRIPTION "Notification of tpNotifyClient1SecmonDbdi."
::= { mxpMIBNotificationPrefix 112 }

tpNotifyClient1SecmonLom OBJECT-TYPE
	SYNTAX      Integer32
	MAX-ACCESS  read-write
	STATUS      current
	DESCRIPTION "client1SecmonLom Notify"
::= { tpNotifyEntry 32 }

tpNotifyClient1SecmonLomNotification NOTIFICATION-TYPE
    OBJECTS { tpNotifyClient1SecmonLom }
    STATUS current
    DESCRIPTION "Notification of tpNotifyClient1SecmonLom."
::= { mxpMIBNotificationPrefix 113 }

tpNotifyClient1PathmonAccstat OBJECT-TYPE
	SYNTAX      Integer32
	MAX-ACCESS  read-write
	STATUS      current
	DESCRIPTION "client1PathmonAccstat Notify"
::= { tpNotifyEntry 33 }

tpNotifyClient1PathmonAccstatNotification NOTIFICATION-TYPE
    OBJECTS { tpNotifyClient1PathmonAccstat }
    STATUS current
    DESCRIPTION "Notification of tpNotifyClient1PathmonAccstat."
::= { mxpMIBNotificationPrefix 114 }

tpNotifyClient1PathmonMsiunst OBJECT-TYPE
	SYNTAX      Integer32
	MAX-ACCESS  read-write
	STATUS      current
	DESCRIPTION "client1PathmonMsiunst Notify"
::= { tpNotifyEntry 34 }

tpNotifyClient1PathmonMsiunstNotification NOTIFICATION-TYPE
    OBJECTS { tpNotifyClient1PathmonMsiunst }
    STATUS current
    DESCRIPTION "Notification of tpNotifyClient1PathmonMsiunst."
::= { mxpMIBNotificationPrefix 115 }

tpNotifyClient1PathmonDais OBJECT-TYPE
	SYNTAX      Integer32
	MAX-ACCESS  read-write
	STATUS      current
	DESCRIPTION "client1PathmonDais Notify"
::= { tpNotifyEntry 35 }

tpNotifyClient1PathmonDaisNotification NOTIFICATION-TYPE
    OBJECTS { tpNotifyClient1PathmonDais }
    STATUS current
    DESCRIPTION "Notification of tpNotifyClient1PathmonDais."
::= { mxpMIBNotificationPrefix 116 }

tpNotifyClient1PathmonDlck OBJECT-TYPE
	SYNTAX      Integer32
	MAX-ACCESS  read-write
	STATUS      current
	DESCRIPTION "client1PathmonDlck Notify"
::= { tpNotifyEntry 36 }

tpNotifyClient1PathmonDlckNotification NOTIFICATION-TYPE
    OBJECTS { tpNotifyClient1PathmonDlck }
    STATUS current
    DESCRIPTION "Notification of tpNotifyClient1PathmonDlck."
::= { mxpMIBNotificationPrefix 117 }

tpNotifyClient1PathmonDbdi OBJECT-TYPE
	SYNTAX      Integer32
	MAX-ACCESS  read-write
	STATUS      current
	DESCRIPTION "client1PathmonDbdi Notify"
::= { tpNotifyEntry 37 }

tpNotifyClient1PathmonDbdiNotification NOTIFICATION-TYPE
    OBJECTS { tpNotifyClient1PathmonDbdi }
    STATUS current
    DESCRIPTION "Notification of tpNotifyClient1PathmonDbdi."
::= { mxpMIBNotificationPrefix 118 }
 
tpNotifyClient2FramerFsmms OBJECT-TYPE
	SYNTAX      Integer32
	MAX-ACCESS  read-write
	STATUS      current
	DESCRIPTION "client2FramerFsmms Notify"
::= { tpNotifyEntry 38 }

tpNotifyClient2FramerFsmmsNotification NOTIFICATION-TYPE
    OBJECTS { tpNotifyClient2FramerFsmms }
    STATUS current
    DESCRIPTION "Notification of tpNotifyClient2FramerFsmms."
::= { mxpMIBNotificationPrefix 119 }

tpNotifyClient2FramerFsusts OBJECT-TYPE
	SYNTAX      Integer32
	MAX-ACCESS  read-write
	STATUS      current
	DESCRIPTION "client2FramerFsusts Notify"
::= { tpNotifyEntry 39 }

tpNotifyClient2FramerFsustsNotification NOTIFICATION-TYPE
    OBJECTS { tpNotifyClient2FramerFsusts }
    STATUS current
    DESCRIPTION "Notification of tpNotifyClient2FramerFsusts."
::= { mxpMIBNotificationPrefix 120 }

tpNotifyClient2FramerSif OBJECT-TYPE
	SYNTAX      Integer32
	MAX-ACCESS  read-write
	STATUS      current
	DESCRIPTION "client2FramerSif Notify"
::= { tpNotifyEntry 40 }

tpNotifyClient2FramerSifNotification NOTIFICATION-TYPE
    OBJECTS { tpNotifyClient2FramerSif }
    STATUS current
    DESCRIPTION "Notification of tpNotifyClient2FramerSif."
::= { mxpMIBNotificationPrefix 121 }

tpNotifyClient2FramerSoof OBJECT-TYPE
	SYNTAX      Integer32
	MAX-ACCESS  read-write
	STATUS      current
	DESCRIPTION "client2FramerSoof Notify"
::= { tpNotifyEntry 41 }

tpNotifyClient2FramerSoofNotification NOTIFICATION-TYPE
    OBJECTS { tpNotifyClient2FramerSoof }
    STATUS current
    DESCRIPTION "Notification of tpNotifyClient2FramerSoof."
::= { mxpMIBNotificationPrefix 122 }

tpNotifyClient2FramerSlof OBJECT-TYPE
	SYNTAX      Integer32
	MAX-ACCESS  read-write
	STATUS      current
	DESCRIPTION "client2FramerSlof Notify"
::= { tpNotifyEntry 42 }

tpNotifyClient2FramerSlofNotification NOTIFICATION-TYPE
    OBJECTS { tpNotifyClient2FramerSlof }
    STATUS current
    DESCRIPTION "Notification of tpNotifyClient2FramerSlof."
::= { mxpMIBNotificationPrefix 123 }

tpNotifyClient2FramerFst OBJECT-TYPE
	SYNTAX      Integer32
	MAX-ACCESS  read-write
	STATUS      current
	DESCRIPTION "client2FramerFst Notify"
::= { tpNotifyEntry 43 }

tpNotifyClient2FramerFstNotification NOTIFICATION-TYPE
    OBJECTS { tpNotifyClient2FramerFst }
    STATUS current
    DESCRIPTION "Notification of tpNotifyClient2FramerFst."
::= { mxpMIBNotificationPrefix 124 }

tpNotifyClient2LosstatLosf OBJECT-TYPE
	SYNTAX      Integer32
	MAX-ACCESS  read-write
	STATUS      current
	DESCRIPTION "client2LosstatLosf Notify"
::= { tpNotifyEntry 44 }

tpNotifyClient2LosstatLosfNotification NOTIFICATION-TYPE
    OBJECTS { tpNotifyClient2LosstatLosf }
    STATUS current
    DESCRIPTION "Notification of tpNotifyClient2LosstatLosf."
::= { mxpMIBNotificationPrefix 125 }

tpNotifyClient2SecmonFlom OBJECT-TYPE
	SYNTAX      Integer32
	MAX-ACCESS  read-write
	STATUS      current
	DESCRIPTION "client2SecmonFlom Notify"
::= { tpNotifyEntry 45 }

tpNotifyClient2SecmonFlomNotification NOTIFICATION-TYPE
    OBJECTS { tpNotifyClient2SecmonFlom }
    STATUS current
    DESCRIPTION "Notification of tpNotifyClient2SecmonFlom."
::= { mxpMIBNotificationPrefix 126 }

tpNotifyClient2SecmonBipsfs OBJECT-TYPE
	SYNTAX      Integer32
	MAX-ACCESS  read-write
	STATUS      current
	DESCRIPTION "client2SecmonBipsfs Notify"
::= { tpNotifyEntry 46 }

tpNotifyClient2SecmonBipsfsNotification NOTIFICATION-TYPE
    OBJECTS { tpNotifyClient2SecmonBipsfs }
    STATUS current
    DESCRIPTION "Notification of tpNotifyClient2SecmonBipsfs."
::= { mxpMIBNotificationPrefix 127 }

tpNotifyClient2SecmonDiae OBJECT-TYPE
	SYNTAX      Integer32
	MAX-ACCESS  read-write
	STATUS      current
	DESCRIPTION "client2SecmonDiae Notify"
::= { tpNotifyEntry 47 }

tpNotifyClient2SecmonDiaeNotification NOTIFICATION-TYPE
    OBJECTS { tpNotifyClient2SecmonDiae }
    STATUS current
    DESCRIPTION "Notification of tpNotifyClient2SecmonDiae."
::= { mxpMIBNotificationPrefix 128 }

tpNotifyClient2SecmonDbdi OBJECT-TYPE
	SYNTAX      Integer32
	MAX-ACCESS  read-write
	STATUS      current
	DESCRIPTION "client2SecmonDbdi Notify"
::= { tpNotifyEntry 48 }

tpNotifyClient2SecmonDbdiNotification NOTIFICATION-TYPE
    OBJECTS { tpNotifyClient2SecmonDbdi }
    STATUS current
    DESCRIPTION "Notification of tpNotifyClient2SecmonDbdi."
::= { mxpMIBNotificationPrefix 129 }

tpNotifyClient2SecmonLom OBJECT-TYPE
	SYNTAX      Integer32
	MAX-ACCESS  read-write
	STATUS      current
	DESCRIPTION "client2SecmonLom Notify"
::= { tpNotifyEntry 49 }

tpNotifyClient2SecmonLomNotification NOTIFICATION-TYPE
    OBJECTS { tpNotifyClient2SecmonLom }
    STATUS current
    DESCRIPTION "Notification of tpNotifyClient2SecmonLom."
::= { mxpMIBNotificationPrefix 130 }

tpNotifyClient2PathmonAccstat OBJECT-TYPE
	SYNTAX      Integer32
	MAX-ACCESS  read-write
	STATUS      current
	DESCRIPTION "client2PathmonAccstat Notify"
::= { tpNotifyEntry 50 }

tpNotifyClient2PathmonAccstatNotification NOTIFICATION-TYPE
    OBJECTS { tpNotifyClient2PathmonAccstat }
    STATUS current
    DESCRIPTION "Notification of tpNotifyClient2PathmonAccstat."
::= { mxpMIBNotificationPrefix 131 }

tpNotifyClient2PathmonMsiunst OBJECT-TYPE
	SYNTAX      Integer32
	MAX-ACCESS  read-write
	STATUS      current
	DESCRIPTION "client2PathmonMsiunst Notify"
::= { tpNotifyEntry 51 }

tpNotifyClient2PathmonMsiunstNotification NOTIFICATION-TYPE
    OBJECTS { tpNotifyClient2PathmonMsiunst }
    STATUS current
    DESCRIPTION "Notification of tpNotifyClient2PathmonMsiunst."
::= { mxpMIBNotificationPrefix 132 }

tpNotifyClient2PathmonDais OBJECT-TYPE
	SYNTAX      Integer32
	MAX-ACCESS  read-write
	STATUS      current
	DESCRIPTION "client2PathmonDais Notify"
::= { tpNotifyEntry 52 }

tpNotifyClient2PathmonDaisNotification NOTIFICATION-TYPE
    OBJECTS { tpNotifyClient2PathmonDais }
    STATUS current
    DESCRIPTION "Notification of tpNotifyClient2PathmonDais."
::= { mxpMIBNotificationPrefix 133 }

tpNotifyClient2PathmonDlck OBJECT-TYPE
	SYNTAX      Integer32
	MAX-ACCESS  read-write
	STATUS      current
	DESCRIPTION "client2PathmonDlck Notify"
::= { tpNotifyEntry 53 }

tpNotifyClient2PathmonDlckNotification NOTIFICATION-TYPE
    OBJECTS { tpNotifyClient2PathmonDlck }
    STATUS current
    DESCRIPTION "Notification of tpNotifyClient2PathmonDlck."
::= { mxpMIBNotificationPrefix 134 }

tpNotifyClient2PathmonDbdi OBJECT-TYPE
	SYNTAX      Integer32
	MAX-ACCESS  read-write
	STATUS      current
	DESCRIPTION "client2PathmonDbdi Notify"
::= { tpNotifyEntry 54 }

tpNotifyClient2PathmonDbdiNotification NOTIFICATION-TYPE
    OBJECTS { tpNotifyClient2PathmonDbdi }
    STATUS current
    DESCRIPTION "Notification of tpNotifyClient2PathmonDbdi."
::= { mxpMIBNotificationPrefix 135 }

tpNotifyClient3FramerFsmms OBJECT-TYPE
	SYNTAX      Integer32
	MAX-ACCESS  read-write
	STATUS      current
	DESCRIPTION "client3FramerFsmms Notify"
::= { tpNotifyEntry 55 }

tpNotifyClient3FramerFsmmsNotification NOTIFICATION-TYPE
    OBJECTS { tpNotifyClient3FramerFsmms }
    STATUS current
    DESCRIPTION "Notification of tpNotifyClient3FramerFsmms."
::= { mxpMIBNotificationPrefix 136 }

tpNotifyClient3FramerFsusts OBJECT-TYPE
	SYNTAX      Integer32
	MAX-ACCESS  read-write
	STATUS      current
	DESCRIPTION "client3FramerFsusts Notify"
::= { tpNotifyEntry 56 }

tpNotifyClient3FramerFsustsNotification NOTIFICATION-TYPE
    OBJECTS { tpNotifyClient3FramerFsusts }
    STATUS current
    DESCRIPTION "Notification of tpNotifyClient3FramerFsusts."
::= { mxpMIBNotificationPrefix 137 }

tpNotifyClient3FramerSif OBJECT-TYPE
	SYNTAX      Integer32
	MAX-ACCESS  read-write
	STATUS      current
	DESCRIPTION "client3FramerSif Notify"
::= { tpNotifyEntry 57 }

tpNotifyClient3FramerSifNotification NOTIFICATION-TYPE
    OBJECTS { tpNotifyClient3FramerSif }
    STATUS current
    DESCRIPTION "Notification of tpNotifyClient3FramerSif."
::= { mxpMIBNotificationPrefix 138 }

tpNotifyClient3FramerSoof OBJECT-TYPE
	SYNTAX      Integer32
	MAX-ACCESS  read-write
	STATUS      current
	DESCRIPTION "client3FramerSoof Notify"
::= { tpNotifyEntry 58 }

tpNotifyClient3FramerSoofNotification NOTIFICATION-TYPE
    OBJECTS { tpNotifyClient3FramerSoof }
    STATUS current
    DESCRIPTION "Notification of tpNotifyClient3FramerSoof."
::= { mxpMIBNotificationPrefix 139 }

tpNotifyClient3FramerSlof OBJECT-TYPE
	SYNTAX      Integer32
	MAX-ACCESS  read-write
	STATUS      current
	DESCRIPTION "client3FramerSlof Notify"
::= { tpNotifyEntry 59 }

tpNotifyClient3FramerSlofNotification NOTIFICATION-TYPE
    OBJECTS { tpNotifyClient3FramerSlof }
    STATUS current
    DESCRIPTION "Notification of tpNotifyClient3FramerSlof."
::= { mxpMIBNotificationPrefix 140 }

tpNotifyClient3FramerFst OBJECT-TYPE
	SYNTAX      Integer32
	MAX-ACCESS  read-write
	STATUS      current
	DESCRIPTION "client3FramerFst Notify"
::= { tpNotifyEntry 60 }

tpNotifyClient3FramerFstNotification NOTIFICATION-TYPE
    OBJECTS { tpNotifyClient3FramerFst }
    STATUS current
    DESCRIPTION "Notification of tpNotifyClient3FramerFst."
::= { mxpMIBNotificationPrefix 141 }

tpNotifyClient3LosstatLosf OBJECT-TYPE
	SYNTAX      Integer32
	MAX-ACCESS  read-write
	STATUS      current
	DESCRIPTION "client3LosstatLosf Notify"
::= { tpNotifyEntry 61 }

tpNotifyClient3LosstatLosfNotification NOTIFICATION-TYPE
    OBJECTS { tpNotifyClient3LosstatLosf }
    STATUS current
    DESCRIPTION "Notification of tpNotifyClient3LosstatLosf."
::= { mxpMIBNotificationPrefix 142 }

tpNotifyClient3SecmonFlom OBJECT-TYPE
	SYNTAX      Integer32
	MAX-ACCESS  read-write
	STATUS      current
	DESCRIPTION "client3SecmonFlom Notify"
::= { tpNotifyEntry 62 }

tpNotifyClient3SecmonFlomNotification NOTIFICATION-TYPE
    OBJECTS { tpNotifyClient3SecmonFlom  }
    STATUS current
    DESCRIPTION "Notification of tpNotifyClient3SecmonFlom."
::= { mxpMIBNotificationPrefix 143 }

tpNotifyClient3SecmonBipsfs OBJECT-TYPE
	SYNTAX      Integer32
	MAX-ACCESS  read-write
	STATUS      current
	DESCRIPTION "client3SecmonBipsfs Notify"
::= { tpNotifyEntry 63 }

tpNotifyClient3SecmonBipsfsNotification NOTIFICATION-TYPE
    OBJECTS { tpNotifyClient3SecmonBipsfs }
    STATUS current
    DESCRIPTION "Notification of tpNotifyClient3SecmonBipsfs."
::= { mxpMIBNotificationPrefix 144 }

tpNotifyClient3SecmonDiae OBJECT-TYPE
	SYNTAX      Integer32
	MAX-ACCESS  read-write
	STATUS      current
	DESCRIPTION "client3SecmonDiae Notify"
::= { tpNotifyEntry 64 }

tpNotifyClient3SecmonDiaeNotification NOTIFICATION-TYPE
    OBJECTS { tpNotifyClient3SecmonDiae }
    STATUS current
    DESCRIPTION "Notification of tpNotifyClient3SecmonDiae."
::= { mxpMIBNotificationPrefix 145 }

tpNotifyClient3SecmonDbdi OBJECT-TYPE
	SYNTAX      Integer32
	MAX-ACCESS  read-write
	STATUS      current
	DESCRIPTION "client3SecmonDbdi Notify"
::= { tpNotifyEntry 65 }

tpNotifyClient3SecmonDbdiNotification NOTIFICATION-TYPE
    OBJECTS { tpNotifyClient3SecmonDbdi }
    STATUS current
    DESCRIPTION "Notification of tpNotifyClient3SecmonDbdi."
::= { mxpMIBNotificationPrefix 146 }

tpNotifyClient3SecmonLom OBJECT-TYPE
	SYNTAX      Integer32
	MAX-ACCESS  read-write
	STATUS      current
	DESCRIPTION "client3SecmonLom Notify"
::= { tpNotifyEntry 66 }

tpNotifyClient3SecmonLomNotification NOTIFICATION-TYPE
    OBJECTS { tpNotifyClient3SecmonLom }
    STATUS current
    DESCRIPTION "Notification of tpNotifyClient3SecmonLom."
::= { mxpMIBNotificationPrefix 147 }

tpNotifyClient3PathmonAccstat OBJECT-TYPE
	SYNTAX      Integer32
	MAX-ACCESS  read-write
	STATUS      current
	DESCRIPTION "client3PathmonAccstat Notify"
::= { tpNotifyEntry 67 }

tpNotifyClient3PathmonAccstatNotification NOTIFICATION-TYPE
    OBJECTS { tpNotifyClient3PathmonAccstat }
    STATUS current
    DESCRIPTION "Notification of tpNotifyClient3PathmonAccstat."
::= { mxpMIBNotificationPrefix 148 }

tpNotifyClient3PathmonMsiunst OBJECT-TYPE
	SYNTAX      Integer32
	MAX-ACCESS  read-write
	STATUS      current
	DESCRIPTION "client3PathmonMsiunst Notify"
::= { tpNotifyEntry 68 }

tpNotifyClient3PathmonMsiunstNotification NOTIFICATION-TYPE
    OBJECTS { tpNotifyClient3PathmonMsiunst }
    STATUS current
    DESCRIPTION "Notification of tpNotifyClient3PathmonMsiunst."
::= { mxpMIBNotificationPrefix 149 }

tpNotifyClient3PathmonDais OBJECT-TYPE
	SYNTAX      Integer32
	MAX-ACCESS  read-write
	STATUS      current
	DESCRIPTION "client3PathmonDais Notify"
::= { tpNotifyEntry 69 }

tpNotifyClient3PathmonDaisNotification NOTIFICATION-TYPE
    OBJECTS { tpNotifyClient3PathmonDais }
    STATUS current
    DESCRIPTION "Notification of tpNotifyClient3PathmonDais."
::= { mxpMIBNotificationPrefix 150 }

tpNotifyClient3PathmonDlck OBJECT-TYPE
	SYNTAX      Integer32
	MAX-ACCESS  read-write
	STATUS      current
	DESCRIPTION "client3PathmonDlck Notify"
::= { tpNotifyEntry 70 }

tpNotifyClient3PathmonDlckNotification NOTIFICATION-TYPE
    OBJECTS { tpNotifyClient3PathmonDlck }
    STATUS current
    DESCRIPTION "Notification of tpNotifyClient3PathmonDlck."
::= { mxpMIBNotificationPrefix 151 }

tpNotifyClient3PathmonDbdi OBJECT-TYPE
	SYNTAX      Integer32
	MAX-ACCESS  read-write
	STATUS      current
	DESCRIPTION "client3PathmonDbdi Notify"
::= { tpNotifyEntry 71 }

tpNotifyClient3PathmonDbdiNotification NOTIFICATION-TYPE
    OBJECTS { tpNotifyClient3PathmonDbdi }
    STATUS current
    DESCRIPTION "Notification of tpNotifyClient3PathmonDbdi."
::= { mxpMIBNotificationPrefix 152 }

tpNotifyClient4FramerFsmms OBJECT-TYPE
	SYNTAX      Integer32
	MAX-ACCESS  read-write
	STATUS      current
	DESCRIPTION "client4FramerFsmms Notify"
::= { tpNotifyEntry 72 }

tpNotifyClient4FramerFsmmsNotification NOTIFICATION-TYPE
    OBJECTS { tpNotifyClient4FramerFsmms }
    STATUS current
    DESCRIPTION "Notification of tpNotifyClient4FramerFsmms."
::= { mxpMIBNotificationPrefix 153 }

tpNotifyClient4FramerFsusts OBJECT-TYPE
	SYNTAX      Integer32
	MAX-ACCESS  read-write
	STATUS      current
	DESCRIPTION "client4FramerFsusts Notify"
::= { tpNotifyEntry 73 }

tpNotifyClient4FramerFsustsNotification NOTIFICATION-TYPE
    OBJECTS { tpNotifyClient4FramerFsusts }
    STATUS current
    DESCRIPTION "Notification of tpNotifyClient4FramerFsusts."
::= { mxpMIBNotificationPrefix 154 }

tpNotifyClient4FramerSif OBJECT-TYPE
	SYNTAX      Integer32
	MAX-ACCESS  read-write
	STATUS      current
	DESCRIPTION "client4FramerSif Notify"
::= { tpNotifyEntry 74 }

tpNotifyClient4FramerSifNotification NOTIFICATION-TYPE
    OBJECTS { tpNotifyClient4FramerSif }
    STATUS current
    DESCRIPTION "Notification of tpNotifyClient4FramerSif."
::= { mxpMIBNotificationPrefix 155 }

tpNotifyClient4FramerSoof OBJECT-TYPE
	SYNTAX      Integer32
	MAX-ACCESS  read-write
	STATUS      current
	DESCRIPTION "client4FramerSoof Notify"
::= { tpNotifyEntry 75 }

tpNotifyClient4FramerSoofNotification NOTIFICATION-TYPE
    OBJECTS { tpNotifyClient4FramerSoof }
    STATUS current
    DESCRIPTION "Notification of tpNotifyClient4FramerSoof."
::= { mxpMIBNotificationPrefix 156 }

tpNotifyClient4FramerSlof OBJECT-TYPE
	SYNTAX      Integer32
	MAX-ACCESS  read-write
	STATUS      current
	DESCRIPTION "client4FramerSlof Notify"
::= { tpNotifyEntry 76 }

tpNotifyClient4FramerSlofNotification NOTIFICATION-TYPE
    OBJECTS { tpNotifyClient4FramerSlof }
    STATUS current
    DESCRIPTION "Notification of tpNotifyClient4FramerSlof."
::= { mxpMIBNotificationPrefix 157 }

tpNotifyClient4FramerFst OBJECT-TYPE
	SYNTAX      Integer32
	MAX-ACCESS  read-write
	STATUS      current
	DESCRIPTION "client4FramerFst Notify"
::= { tpNotifyEntry 77 }

tpNotifyClient4FramerFstNotification NOTIFICATION-TYPE
    OBJECTS { tpNotifyClient4FramerFst }
    STATUS current
    DESCRIPTION "Notification of tpNotifyClient4FramerFst."
::= { mxpMIBNotificationPrefix 158 }

tpNotifyClient4LosstatLosf OBJECT-TYPE
	SYNTAX      Integer32
	MAX-ACCESS  read-write
	STATUS      current
	DESCRIPTION "client4LosstatLosf Notify"
::= { tpNotifyEntry 78 }

tpNotifyClient4LosstatLosfNotification NOTIFICATION-TYPE
    OBJECTS { tpNotifyClient4LosstatLosf }
    STATUS current
    DESCRIPTION "Notification of tpNotifyClient4LosstatLosf."
::= { mxpMIBNotificationPrefix 159 }

tpNotifyClient4SecmonFlom OBJECT-TYPE
	SYNTAX      Integer32
	MAX-ACCESS  read-write
	STATUS      current
	DESCRIPTION "client4SecmonFlom Notify"
::= { tpNotifyEntry 79 }

tpNotifyClient4SecmonFlomNotification NOTIFICATION-TYPE
    OBJECTS { tpNotifyClient4SecmonFlom }
    STATUS current
    DESCRIPTION "Notification of tpNotifyClient4SecmonFlom."
::= { mxpMIBNotificationPrefix 160 }

tpNotifyClient4SecmonBipsfs OBJECT-TYPE
	SYNTAX      Integer32
	MAX-ACCESS  read-write
	STATUS      current
	DESCRIPTION "client4SecmonBipsfs Notify"
::= { tpNotifyEntry 80 }

tpNotifyClient4SecmonBipsfsNotification NOTIFICATION-TYPE
    OBJECTS { tpNotifyClient4SecmonBipsfs }
    STATUS current
    DESCRIPTION "Notification of tpNotifyClient4SecmonBipsfs."
::= { mxpMIBNotificationPrefix 161 }

tpNotifyClient4SecmonDiae OBJECT-TYPE
	SYNTAX      Integer32
	MAX-ACCESS  read-write
	STATUS      current
	DESCRIPTION "client4SecmonDiae Notify"
::= { tpNotifyEntry 81 }

tpNotifyClient4SecmonDiaeNotification NOTIFICATION-TYPE
    OBJECTS { tpNotifyClient4SecmonDiae }
    STATUS current
    DESCRIPTION "Notification of tpNotifyClient4SecmonDiae."
::= { mxpMIBNotificationPrefix 162 }

tpNotifyClient4SecmonDbdi OBJECT-TYPE
	SYNTAX      Integer32
	MAX-ACCESS  read-write
	STATUS      current
	DESCRIPTION "client4SecmonDbdi Notify"
::= { tpNotifyEntry 82 }

tpNotifyClient4SecmonDbdiNotification NOTIFICATION-TYPE
    OBJECTS { tpNotifyClient4SecmonDbdi }
    STATUS current
    DESCRIPTION "Notification of tpNotifyClient4SecmonDbdi."
::= { mxpMIBNotificationPrefix 163 }

tpNotifyClient4SecmonLom OBJECT-TYPE
	SYNTAX      Integer32
	MAX-ACCESS  read-write
	STATUS      current
	DESCRIPTION "client4SecmonLom Notify"
::= { tpNotifyEntry 83 }

tpNotifyClient4SecmonLomNotification NOTIFICATION-TYPE
    OBJECTS { tpNotifyClient4SecmonLom }
    STATUS current
    DESCRIPTION "Notification of tpNotifyClient4SecmonLom."
::= { mxpMIBNotificationPrefix 164 }

tpNotifyClient4PathmonAccstat OBJECT-TYPE
	SYNTAX      Integer32
	MAX-ACCESS  read-write
	STATUS      current
	DESCRIPTION "client4PathmonAccstat Notify"
::= { tpNotifyEntry 84 }

tpNotifyClient4PathmonAccstatNotification NOTIFICATION-TYPE
    OBJECTS { tpNotifyClient4PathmonAccstat }
    STATUS current
    DESCRIPTION "Notification of tpNotifyClient4PathmonAccstat."
::= { mxpMIBNotificationPrefix 165 }

tpNotifyClient4PathmonMsiunst OBJECT-TYPE
	SYNTAX      Integer32
	MAX-ACCESS  read-write
	STATUS      current
	DESCRIPTION "client4PathmonMsiunst Notify"
::= { tpNotifyEntry 85 }

tpNotifyClient4PathmonMsiunstNotification NOTIFICATION-TYPE
    OBJECTS { tpNotifyClient4PathmonMsiunst }
    STATUS current
    DESCRIPTION "Notification of tpNotifyClient4PathmonMsiunst."
::= { mxpMIBNotificationPrefix 166 }

tpNotifyClient4PathmonDais OBJECT-TYPE
	SYNTAX      Integer32
	MAX-ACCESS  read-write
	STATUS      current
	DESCRIPTION "client4PathmonDais Notify"
::= { tpNotifyEntry 86 }

tpNotifyClient4PathmonDaisNotification NOTIFICATION-TYPE
    OBJECTS { tpNotifyClient4PathmonDais }
    STATUS current
    DESCRIPTION "Notification of tpNotifyClient4PathmonDais."
::= { mxpMIBNotificationPrefix 167 }

tpNotifyClient4PathmonDlck OBJECT-TYPE
	SYNTAX      Integer32
	MAX-ACCESS  read-write
	STATUS      current
	DESCRIPTION "client4PathmonDlck Notify"
::= { tpNotifyEntry 87 }

tpNotifyClient4PathmonDlckNotification NOTIFICATION-TYPE
    OBJECTS { tpNotifyClient4PathmonDlck }
    STATUS current
    DESCRIPTION "Notification of tpNotifyClient4PathmonDlck."
::= { mxpMIBNotificationPrefix 168 }

tpNotifyClient4PathmonDbdi OBJECT-TYPE
	SYNTAX      Integer32
	MAX-ACCESS  read-write
	STATUS      current
	DESCRIPTION "client4PathmonDbdi Notify"
::= { tpNotifyEntry 88 }

tpNotifyClient4PathmonDbdiNotification NOTIFICATION-TYPE
    OBJECTS { tpNotifyClient4PathmonDbdi }
    STATUS current
    DESCRIPTION "Notification of tpNotifyClient4PathmonDbdi."
::= { mxpMIBNotificationPrefix 169 }

tpNotifyGroup OBJECT-GROUP
    OBJECTS { tpNotifyLineFramerFsmmtrb3s, tpNotifyLineFramerFsmmtrb2s, tpNotifyLineFramerFsmmtrb1s, tpNotifyLineFramerFsmms, tpNotifyLineFramerSif, tpNotifyLineFramerSoof, tpNotifyLineFramerSlof, tpNotifyLineFramerFst, tpNotifyLineLosstatLosf, tpNotifyLineSecmonFlom, tpNotifyLineSecmonBipsfs, tpNotifyLineSecmonDiae, tpNotifyLineSecmonDbdi, tpNotifyLineSecmonLom, tpNotifyLinePathmonAccstat, tpNotifyLinePathmonMsiunst, tpNotifyLinePathmonDais, tpNotifyLinePathmonDlck, tpNotifyLinePathmonDbdi, tpNotifyClient1FramerFsmms, tpNotifyClient1FramerFsusts, tpNotifyClient1FramerSif, tpNotifyClient1FramerSoof, tpNotifyClient1FramerSlof, tpNotifyClient1FramerFst, tpNotifyClient1LosstatLosf, tpNotifyClient1SecmonFlom, tpNotifyClient1SecmonBipsfs, tpNotifyClient1SecmonDiae, tpNotifyClient1SecmonDbdi, tpNotifyClient1SecmonLom, tpNotifyClient1PathmonAccstat, tpNotifyClient1PathmonMsiunst, tpNotifyClient1PathmonDais, tpNotifyClient1PathmonDlck, tpNotifyClient1PathmonDbdi, tpNotifyClient2FramerFsmms, tpNotifyClient2FramerFsusts, tpNotifyClient2FramerSif, tpNotifyClient2FramerSoof, tpNotifyClient2FramerSlof, tpNotifyClient2FramerFst, tpNotifyClient2LosstatLosf, tpNotifyClient2SecmonFlom, tpNotifyClient2SecmonBipsfs, tpNotifyClient2SecmonDiae, tpNotifyClient2SecmonDbdi, tpNotifyClient2SecmonLom, tpNotifyClient2PathmonAccstat, tpNotifyClient2PathmonMsiunst, tpNotifyClient2PathmonDais, tpNotifyClient2PathmonDlck, tpNotifyClient2PathmonDbdi, tpNotifyClient3FramerFsmms, tpNotifyClient3FramerFsusts, tpNotifyClient3FramerSif, tpNotifyClient3FramerSoof, tpNotifyClient3FramerSlof, tpNotifyClient3FramerFst, tpNotifyClient3LosstatLosf, tpNotifyClient3SecmonFlom, tpNotifyClient3SecmonBipsfs, tpNotifyClient3SecmonDiae, tpNotifyClient3SecmonDbdi, tpNotifyClient3SecmonLom, tpNotifyClient3PathmonAccstat, tpNotifyClient3PathmonMsiunst, tpNotifyClient3PathmonDais, tpNotifyClient3PathmonDlck, tpNotifyClient3PathmonDbdi, tpNotifyClient4FramerFsmms, tpNotifyClient4FramerFsusts, tpNotifyClient4FramerSif, tpNotifyClient4FramerSoof, tpNotifyClient4FramerSlof, tpNotifyClient4FramerFst, tpNotifyClient4LosstatLosf, tpNotifyClient4SecmonFlom, tpNotifyClient4SecmonBipsfs, tpNotifyClient4SecmonDiae, tpNotifyClient4SecmonDbdi, tpNotifyClient4SecmonLom, tpNotifyClient4PathmonAccstat, tpNotifyClient4PathmonMsiunst, tpNotifyClient4PathmonDais, tpNotifyClient4PathmonDlck, tpNotifyClient4PathmonDbdi }
    STATUS  current
    DESCRIPTION "The tpNotifyGroup, objects of Traffic Processor notify."
    ::= { mxpNotifyGroups 7 }

tpNotificationGroup NOTIFICATION-GROUP
    NOTIFICATIONS { tpNotifyLineFramerFsmmtrb3sNotification, tpNotifyLineFramerFsmmtrb2sNotification, tpNotifyLineFramerFsmmtrb1sNotification, tpNotifyLineFramerFsmmsNotification, tpNotifyLineFramerSifNotification, tpNotifyLineFramerSoofNotification, tpNotifyLineFramerSlofNotification, tpNotifyLineFramerFstNotification, tpNotifyLineLosstatLosfNotification, tpNotifyLineSecmonFlomNotification, tpNotifyLineSecmonBipsfsNotification, tpNotifyLineSecmonDiaeNotification, tpNotifyLineSecmonDbdiNotification, tpNotifyLineSecmonLomNotification, tpNotifyLinePathmonAccstatNotification, tpNotifyLinePathmonMsiunstNotification, tpNotifyLinePathmonDaisNotification, tpNotifyLinePathmonDlckNotification, tpNotifyLinePathmonDbdiNotification, tpNotifyClient1FramerFsmmsNotification, tpNotifyClient1FramerFsustsNotification, tpNotifyClient1FramerSifNotification, tpNotifyClient1FramerSoofNotification, tpNotifyClient1FramerSlofNotification, tpNotifyClient1FramerFstNotification, tpNotifyClient1LosstatLosfNotification, tpNotifyClient1SecmonFlomNotification, tpNotifyClient1SecmonBipsfsNotification, tpNotifyClient1SecmonDiaeNotification, tpNotifyClient1SecmonDbdiNotification, tpNotifyClient1SecmonLomNotification, tpNotifyClient1PathmonAccstatNotification, tpNotifyClient1PathmonMsiunstNotification, tpNotifyClient1PathmonDaisNotification, tpNotifyClient1PathmonDlckNotification, tpNotifyClient1PathmonDbdiNotification, tpNotifyClient2FramerFsmmsNotification, tpNotifyClient2FramerFsustsNotification, tpNotifyClient2FramerSifNotification, tpNotifyClient2FramerSoofNotification, tpNotifyClient2FramerSlofNotification, tpNotifyClient2FramerFstNotification, tpNotifyClient2LosstatLosfNotification, tpNotifyClient2SecmonFlomNotification, tpNotifyClient2SecmonBipsfsNotification, tpNotifyClient2SecmonDiaeNotification, tpNotifyClient2SecmonDbdiNotification, tpNotifyClient2SecmonLomNotification, tpNotifyClient2PathmonAccstatNotification, tpNotifyClient2PathmonMsiunstNotification, tpNotifyClient2PathmonDaisNotification, tpNotifyClient2PathmonDlckNotification, tpNotifyClient2PathmonDbdiNotification, tpNotifyClient3FramerFsmmsNotification, tpNotifyClient3FramerFsustsNotification, tpNotifyClient3FramerSifNotification, tpNotifyClient3FramerSoofNotification, tpNotifyClient3FramerSlofNotification, tpNotifyClient3FramerFstNotification, tpNotifyClient3LosstatLosfNotification, tpNotifyClient3SecmonFlomNotification, tpNotifyClient3SecmonBipsfsNotification, tpNotifyClient3SecmonDiaeNotification, tpNotifyClient3SecmonDbdiNotification, tpNotifyClient3SecmonLomNotification, tpNotifyClient3PathmonAccstatNotification, tpNotifyClient3PathmonMsiunstNotification, tpNotifyClient3PathmonDaisNotification, tpNotifyClient3PathmonDlckNotification, tpNotifyClient3PathmonDbdiNotification, tpNotifyClient4FramerFsmmsNotification, tpNotifyClient4FramerFsustsNotification, tpNotifyClient4FramerSifNotification, tpNotifyClient4FramerSoofNotification, tpNotifyClient4FramerSlofNotification, tpNotifyClient4FramerFstNotification, tpNotifyClient4LosstatLosfNotification, tpNotifyClient4SecmonFlomNotification, tpNotifyClient4SecmonBipsfsNotification, tpNotifyClient4SecmonDiaeNotification, tpNotifyClient4SecmonDbdiNotification, tpNotifyClient4SecmonLomNotification, tpNotifyClient4PathmonAccstatNotification, tpNotifyClient4PathmonMsiunstNotification, tpNotifyClient4PathmonDaisNotification, tpNotifyClient4PathmonDlckNotification, tpNotifyClient4PathmonDbdiNotification }
    STATUS  current
    DESCRIPTION "The tpNotificationGroup, grouping notifications of Traffic Processor."
    ::= { mxpNotificationGroups 7 }


-- MXP Severity MIB

mxpSeverityMIB OBJECT IDENTIFIER ::= { mxp 3 }

mxpSeverityMIBConformance OBJECT IDENTIFIER ::= { mxpSeverityMIB 1 }

mxpSeverityMIBCompliances OBJECT IDENTIFIER ::= { mxpSeverityMIBConformance 1 }

mxpSeverityMIBGroups OBJECT IDENTIFIER ::= { mxpSeverityMIB 2 }

edfaAlarms       OBJECT IDENTIFIER ::= { mxpSeverityMIB 3 }
txpAlarms       OBJECT IDENTIFIER ::= { mxpSeverityMIB 4 }
xfpAlarms       OBJECT IDENTIFIER ::= { mxpSeverityMIB 5 }
tpAlarms       OBJECT IDENTIFIER ::= { mxpSeverityMIB 6 }

alarmBasicCompliance MODULE-COMPLIANCE
    STATUS  current
    DESCRIPTION
            "The compliance statement for alarm entities which
            implement this MIB module."
    MODULE  -- this module
        MANDATORY-GROUPS { edfaSeverityGroup, txpSeverityGroup, xfp1SeverityGroup, xfp2SeverityGroup, xfp3SeverityGroup, xfp4SeverityGroup,
        tpLineSeverityGroup, tpClient1SeverityGroup, tpClient2SeverityGroup, tpClient3SeverityGroup, tpClient4SeverityGroup}

    ::= { mxpSeverityMIBCompliances 1 }

--
-- Table for edfa
--
edfaSeverityTable OBJECT-TYPE
	SYNTAX SEQUENCE OF EdfaSeverityEntry
	MAX-ACCESS not-accessible
	STATUS current
	DESCRIPTION "A table containing information on edfa."
::= { edfaAlarms 1 }

edfaSeverityEntry OBJECT-TYPE
	SYNTAX	EdfaSeverityEntry
	MAX-ACCESS	not-accessible
	STATUS	current
	DESCRIPTION "An entry of the edfa table."
	INDEX	{ edfaSeverityIndex }
::= { edfaSeverityTable  1 }

EdfaSeverityEntry ::= SEQUENCE { edfaSeverityIndex Integer32, edfaSeverityAmpStatus Integer32, edfaSeverityInputPower Integer32, edfaSeverityLop Integer32, 
 edfaSeverityLos Integer32, edfaSeverityOutputPower Integer32, edfaSeverityTemperature Integer32}

edfaSeverityIndex OBJECT-TYPE
	SYNTAX	Integer32 (0..65535)
	MAX-ACCESS	not-accessible
	STATUS	current
	DESCRIPTION "The auxiliary variable used for identifying instances
            of the columnar objects in the edfaSeverityTable"
::= { edfaSeverityEntry 1 }

edfaSeverityAmpStatus OBJECT-TYPE
	SYNTAX      Integer32
	MAX-ACCESS  read-write
	STATUS      current
	DESCRIPTION "alarm severity"
::= { edfaSeverityEntry 2 }

edfaSeverityInputPower OBJECT-TYPE
	SYNTAX      Integer32
	MAX-ACCESS  read-write
	STATUS      current
	DESCRIPTION "alarm severity"
::= { edfaSeverityEntry 3 }

edfaSeverityLop OBJECT-TYPE
	SYNTAX      Integer32
	MAX-ACCESS  read-write
	STATUS      current
	DESCRIPTION "alarm severity"
::= { edfaSeverityEntry 4 }

edfaSeverityLos OBJECT-TYPE
	SYNTAX      Integer32
	MAX-ACCESS  read-write
	STATUS      current
	DESCRIPTION "alarm severity"
::= { edfaSeverityEntry 5 }

edfaSeverityOutputPower OBJECT-TYPE
	SYNTAX      Integer32
	MAX-ACCESS  read-write
	STATUS      current
	DESCRIPTION "alarm severity"
::= { edfaSeverityEntry 6 }

edfaSeverityTemperature OBJECT-TYPE
	SYNTAX      Integer32
	MAX-ACCESS  read-write
	STATUS      current
	DESCRIPTION "alarm severity"
::= { edfaSeverityEntry 7 }

edfaSeverityGroup OBJECT-GROUP
    OBJECTS { edfaSeverityAmpStatus, edfaSeverityInputPower, edfaSeverityLop, edfaSeverityLos, edfaSeverityOutputPower, edfaSeverityTemperature }
    STATUS  current
    DESCRIPTION
        "The edfaSeverityGroup, groups objects of edfa."
    ::= { mxpSeverityMIBGroups 1 }

--
-- Table for txp
--
txpSeverityTable OBJECT-TYPE
	SYNTAX SEQUENCE OF TxpSeverityEntry
	MAX-ACCESS not-accessible
	STATUS current
	DESCRIPTION "A table containing information on txp."
::= { txpAlarms 1 }

txpSeverityEntry OBJECT-TYPE
	SYNTAX	TxpSeverityEntry
	MAX-ACCESS	not-accessible
	STATUS	current
	DESCRIPTION "An entry of the txp table."
	INDEX	{ txpSeverityIndex }
::= { txpSeverityTable  1 }

TxpSeverityEntry ::= SEQUENCE { txpSeverityIndex Integer32, txpSeverityEol Integer32, txpSeverityModTemp Integer32, txpSeverityTxooa Integer32, txpSeverityTxLof Integer32, 
 txpSeverityTxDsc Integer32, txpSeverityLsWav Integer32, txpSeverityLsBias Integer32, txpSeverityLsTemp Integer32, txpSeverityTxLock Integer32, txpSeverityLsPow Integer32, 
 txpSeverityModBias Integer32, txpSeverityLatchedTxFifo Integer32, txpSeverityRxPow Integer32, txpSeverityRxLos Integer32, txpSeverityRxLock Integer32, txpSeverityRxs Integer32, 
 txpSeverityPrbsErr Integer32, txpSeverityPsummary Integer32, txpSeverityP5vAnalog Integer32, txpSeverityN5v2Analog Integer32, txpSeverityP3p3vAnalog Integer32, 
 txpSeverityP3p3vDigital Integer32, txpSeverityLvDigital Integer32, txpSeverityN5p2vDigital Integer32}

txpSeverityIndex OBJECT-TYPE
	SYNTAX	Integer32 (0..65535)
	MAX-ACCESS	not-accessible
	STATUS	current
	DESCRIPTION "The auxiliary variable used for identifying instances
            of the columnar objects in the txpSeverityTable"
::= { txpSeverityEntry 1 }

txpSeverityEol OBJECT-TYPE
	SYNTAX      Integer32
	MAX-ACCESS  read-write
	STATUS      current
	DESCRIPTION "alarm severity"
::= { txpSeverityEntry 2 }

txpSeverityModTemp OBJECT-TYPE
	SYNTAX      Integer32
	MAX-ACCESS  read-write
	STATUS      current
	DESCRIPTION "alarm severity"
::= { txpSeverityEntry 3 }

txpSeverityTxooa OBJECT-TYPE
	SYNTAX      Integer32
	MAX-ACCESS  read-write
	STATUS      current
	DESCRIPTION "alarm severity"
::= { txpSeverityEntry 4 }

txpSeverityTxLof OBJECT-TYPE
	SYNTAX      Integer32
	MAX-ACCESS  read-write
	STATUS      current
	DESCRIPTION "alarm severity"
::= { txpSeverityEntry 5 }

txpSeverityTxDsc OBJECT-TYPE
	SYNTAX      Integer32
	MAX-ACCESS  read-write
	STATUS      current
	DESCRIPTION "alarm severity"
::= { txpSeverityEntry 6 }

txpSeverityLsWav OBJECT-TYPE
	SYNTAX      Integer32
	MAX-ACCESS  read-write
	STATUS      current
	DESCRIPTION "alarm severity"
::= { txpSeverityEntry 7 }

txpSeverityLsBias OBJECT-TYPE
	SYNTAX      Integer32
	MAX-ACCESS  read-write
	STATUS      current
	DESCRIPTION "alarm severity"
::= { txpSeverityEntry 8 }

txpSeverityLsTemp OBJECT-TYPE
	SYNTAX      Integer32
	MAX-ACCESS  read-write
	STATUS      current
	DESCRIPTION "alarm severity"
::= { txpSeverityEntry 9 }

txpSeverityTxLock OBJECT-TYPE
	SYNTAX      Integer32
	MAX-ACCESS  read-write
	STATUS      current
	DESCRIPTION "alarm severity"
::= { txpSeverityEntry 10 }

txpSeverityLsPow OBJECT-TYPE
	SYNTAX      Integer32
	MAX-ACCESS  read-write
	STATUS      current
	DESCRIPTION "alarm severity"
::= { txpSeverityEntry 11 }

txpSeverityModBias OBJECT-TYPE
	SYNTAX      Integer32
	MAX-ACCESS  read-write
	STATUS      current
	DESCRIPTION "alarm severity"
::= { txpSeverityEntry 12 }

txpSeverityLatchedTxFifo OBJECT-TYPE
	SYNTAX      Integer32
	MAX-ACCESS  read-write
	STATUS      current
	DESCRIPTION "alarm severity"
::= { txpSeverityEntry 13 }

txpSeverityRxPow OBJECT-TYPE
	SYNTAX      Integer32
	MAX-ACCESS  read-write
	STATUS      current
	DESCRIPTION "alarm severity"
::= { txpSeverityEntry 14 }

txpSeverityRxLos OBJECT-TYPE
	SYNTAX      Integer32
	MAX-ACCESS  read-write
	STATUS      current
	DESCRIPTION "alarm severity"
::= { txpSeverityEntry 15 }

txpSeverityRxLock OBJECT-TYPE
	SYNTAX      Integer32
	MAX-ACCESS  read-write
	STATUS      current
	DESCRIPTION "alarm severity"
::= { txpSeverityEntry 16 }

txpSeverityRxs OBJECT-TYPE
	SYNTAX      Integer32
	MAX-ACCESS  read-write
	STATUS      current
	DESCRIPTION "alarm severity"
::= { txpSeverityEntry 17 }

txpSeverityPrbsErr OBJECT-TYPE
	SYNTAX      Integer32
	MAX-ACCESS  read-write
	STATUS      current
	DESCRIPTION "alarm severity"
::= { txpSeverityEntry 18 }

txpSeverityPsummary OBJECT-TYPE
	SYNTAX      Integer32
	MAX-ACCESS  read-write
	STATUS      current
	DESCRIPTION "alarm severity"
::= { txpSeverityEntry 19 }

txpSeverityP5vAnalog OBJECT-TYPE
	SYNTAX      Integer32
	MAX-ACCESS  read-write
	STATUS      current
	DESCRIPTION "alarm severity"
::= { txpSeverityEntry 20 }

txpSeverityN5v2Analog OBJECT-TYPE
	SYNTAX      Integer32
	MAX-ACCESS  read-write
	STATUS      current
	DESCRIPTION "alarm severity"
::= { txpSeverityEntry 21 }

txpSeverityP3p3vAnalog OBJECT-TYPE
	SYNTAX      Integer32
	MAX-ACCESS  read-write
	STATUS      current
	DESCRIPTION "alarm severity"
::= { txpSeverityEntry 22 }

txpSeverityP3p3vDigital OBJECT-TYPE
	SYNTAX      Integer32
	MAX-ACCESS  read-write
	STATUS      current
	DESCRIPTION "alarm severity"
::= { txpSeverityEntry 23 }

txpSeverityLvDigital OBJECT-TYPE
	SYNTAX      Integer32
	MAX-ACCESS  read-write
	STATUS      current
	DESCRIPTION "alarm severity"
::= { txpSeverityEntry 24 }

txpSeverityN5p2vDigital OBJECT-TYPE
	SYNTAX      Integer32
	MAX-ACCESS  read-write
	STATUS      current
	DESCRIPTION "alarm severity"
::= { txpSeverityEntry 25 }

txpSeverityGroup OBJECT-GROUP
    OBJECTS { txpSeverityEol, txpSeverityModTemp, txpSeverityTxooa, txpSeverityTxLof, txpSeverityTxDsc, txpSeverityLsWav, txpSeverityLsBias, txpSeverityLsTemp, txpSeverityTxLock, 
    txpSeverityLsPow, txpSeverityModBias, txpSeverityLatchedTxFifo, txpSeverityRxPow, txpSeverityRxLos, txpSeverityRxLock, txpSeverityRxs, txpSeverityPrbsErr, txpSeverityPsummary,
    txpSeverityP5vAnalog, txpSeverityN5v2Analog, txpSeverityP3p3vAnalog, txpSeverityP3p3vDigital , txpSeverityLvDigital, txpSeverityN5p2vDigital}
    STATUS  current
    DESCRIPTION
        "The txpSeverityGroup, groups objects of txp."
    ::= { mxpSeverityMIBGroups 2 }

--
-- Table for xfp1Severity
--
xfp1SeverityTable OBJECT-TYPE
	SYNTAX SEQUENCE OF Xfp1SeverityEntry
	MAX-ACCESS not-accessible
	STATUS current
	DESCRIPTION "A table containing information on xfp1Severity."
::= { xfpAlarms 1 }

xfp1SeverityEntry OBJECT-TYPE
	SYNTAX	Xfp1SeverityEntry
	MAX-ACCESS	not-accessible
	STATUS	current
	DESCRIPTION "An entry of the xfp1Severity table."
	INDEX	{ xfp1SeverityIndex }
::= { xfp1SeverityTable  1 }

Xfp1SeverityEntry ::= SEQUENCE { xfp1SeverityIndex Integer32, xfp1SeverityPresence Integer32, xfp1SeverityRxLoss Integer32, xfp1SeverityReady Integer32,
 xfp1SeverityTxPower Integer32, xfp1SeverityRxPower Integer32, xfp1SeverityTemperature Integer32, xfp1SeverityLowTxPower Integer32, xfp1SeverityHighTxPower Integer32, 
 xfp1SeverityLowRxPower Integer32, xfp1SeverityHighRxPower Integer32, xfp1SeverityRxCdrLossOfLock Integer32, xfp1SeverityTxCdrLossOfLock Integer32, xfp1SeverityLaserFault Integer32}

xfp1SeverityIndex OBJECT-TYPE
	SYNTAX	Integer32 (0..65535)
	MAX-ACCESS	not-accessible
	STATUS	current
	DESCRIPTION "The auxiliary variable used for identifying instances
            of the columnar objects in the xfpTable"
::= { xfp1SeverityEntry 1 }

xfp1SeverityPresence OBJECT-TYPE
	SYNTAX      Integer32
	MAX-ACCESS  read-write
	STATUS      current
	DESCRIPTION "alarm severity"
::= { xfp1SeverityEntry 2 }

xfp1SeverityRxLoss OBJECT-TYPE
	SYNTAX      Integer32
	MAX-ACCESS  read-write
	STATUS      current
	DESCRIPTION "alarm severity"
::= { xfp1SeverityEntry 3 }

xfp1SeverityReady OBJECT-TYPE
	SYNTAX      Integer32
	MAX-ACCESS  read-write
	STATUS      current
	DESCRIPTION "alarm severity"
::= { xfp1SeverityEntry 4 }

xfp1SeverityTxPower OBJECT-TYPE
	SYNTAX      Integer32
	MAX-ACCESS  read-write
	STATUS      current
	DESCRIPTION "alarm severity"
::= { xfp1SeverityEntry 5 }

xfp1SeverityRxPower OBJECT-TYPE
	SYNTAX      Integer32
	MAX-ACCESS  read-write
	STATUS      current
	DESCRIPTION "alarm severity"
::= { xfp1SeverityEntry 6 }

xfp1SeverityTemperature OBJECT-TYPE
	SYNTAX      Integer32
	MAX-ACCESS  read-write
	STATUS      current
	DESCRIPTION "alarm severity"
::= { xfp1SeverityEntry 7 }

xfp1SeverityLowTxPower OBJECT-TYPE
	SYNTAX      Integer32
	MAX-ACCESS  read-write
	STATUS      current
	DESCRIPTION "alarm severity"
::= { xfp1SeverityEntry 8 }

xfp1SeverityHighTxPower OBJECT-TYPE
	SYNTAX      Integer32
	MAX-ACCESS  read-write
	STATUS      current
	DESCRIPTION "alarm severity"
::= { xfp1SeverityEntry 9 }

xfp1SeverityLowRxPower OBJECT-TYPE
	SYNTAX      Integer32
	MAX-ACCESS  read-write
	STATUS      current
	DESCRIPTION "alarm severity"
::= { xfp1SeverityEntry 10 }

xfp1SeverityHighRxPower OBJECT-TYPE
	SYNTAX      Integer32
	MAX-ACCESS  read-write
	STATUS      current
	DESCRIPTION "alarm severity"
::= { xfp1SeverityEntry 11 }

xfp1SeverityRxCdrLossOfLock OBJECT-TYPE
	SYNTAX      Integer32
	MAX-ACCESS  read-write
	STATUS      current
	DESCRIPTION "alarm severity"
::= { xfp1SeverityEntry 12 }

xfp1SeverityTxCdrLossOfLock OBJECT-TYPE
	SYNTAX      Integer32
	MAX-ACCESS  read-write
	STATUS      current
	DESCRIPTION "alarm severity"
::= { xfp1SeverityEntry 13 }

xfp1SeverityLaserFault OBJECT-TYPE
	SYNTAX      Integer32
	MAX-ACCESS  read-write
	STATUS      current
	DESCRIPTION "alarm severity"
::= { xfp1SeverityEntry 14 }

xfp1SeverityGroup OBJECT-GROUP
    OBJECTS { xfp1SeverityPresence, xfp1SeverityRxLoss, xfp1SeverityReady, xfp1SeverityTxPower, xfp1SeverityRxPower, 
    xfp1SeverityTemperature, xfp1SeverityLowTxPower, xfp1SeverityHighTxPower, xfp1SeverityLowRxPower, 
    xfp1SeverityHighRxPower, xfp1SeverityRxCdrLossOfLock, xfp1SeverityTxCdrLossOfLock, xfp1SeverityLaserFault }
    STATUS  current
    DESCRIPTION
        "The xfp1SeverityGroup, groups objects of xfp1Severity."
    ::= { mxpSeverityMIBGroups 3 }

--
-- Table for xfp2Severity
--
xfp2SeverityTable OBJECT-TYPE
	SYNTAX SEQUENCE OF Xfp2SeverityEntry
	MAX-ACCESS not-accessible
	STATUS current
	DESCRIPTION "A table containing information on xfp2Severity."
::= { xfpAlarms 2 }

xfp2SeverityEntry OBJECT-TYPE
	SYNTAX	Xfp2SeverityEntry
	MAX-ACCESS	not-accessible
	STATUS	current
	DESCRIPTION "An entry of the xfp2Severity table."
	INDEX	{ xfp2SeverityIndex }
::= { xfp2SeverityTable  1 }

Xfp2SeverityEntry ::= SEQUENCE { xfp2SeverityIndex Integer32, xfp2SeverityPresence Integer32, xfp2SeverityRxLoss Integer32, xfp2SeverityReady Integer32,
 xfp2SeverityTxPower Integer32, xfp2SeverityRxPower Integer32, xfp2SeverityTemperature Integer32, xfp2SeverityLowTxPower Integer32, xfp2SeverityHighTxPower Integer32, 
 xfp2SeverityLowRxPower Integer32, xfp2SeverityHighRxPower Integer32, xfp2SeverityRxCdrLossOfLock Integer32, xfp2SeverityTxCdrLossOfLock Integer32, xfp2SeverityLaserFault Integer32}

xfp2SeverityIndex OBJECT-TYPE
	SYNTAX	Integer32 (0..65535)
	MAX-ACCESS	not-accessible
	STATUS	current
	DESCRIPTION "The auxiliary variable used for identifying instances
            of the columnar objects in the xfpTable"
::= { xfp2SeverityEntry 1 }

xfp2SeverityPresence OBJECT-TYPE
	SYNTAX      Integer32
	MAX-ACCESS  read-write
	STATUS      current
	DESCRIPTION "alarm severity"
::= { xfp2SeverityEntry 2 }

xfp2SeverityRxLoss OBJECT-TYPE
	SYNTAX      Integer32
	MAX-ACCESS  read-write
	STATUS      current
	DESCRIPTION "alarm severity"
::= { xfp2SeverityEntry 3 }

xfp2SeverityReady OBJECT-TYPE
	SYNTAX      Integer32
	MAX-ACCESS  read-write
	STATUS      current
	DESCRIPTION "alarm severity"
::= { xfp2SeverityEntry 4 }

xfp2SeverityTxPower OBJECT-TYPE
	SYNTAX      Integer32
	MAX-ACCESS  read-write
	STATUS      current
	DESCRIPTION "alarm severity"
::= { xfp2SeverityEntry 5 }

xfp2SeverityRxPower OBJECT-TYPE
	SYNTAX      Integer32
	MAX-ACCESS  read-write
	STATUS      current
	DESCRIPTION "alarm severity"
::= { xfp2SeverityEntry 6 }

xfp2SeverityTemperature OBJECT-TYPE
	SYNTAX      Integer32
	MAX-ACCESS  read-write
	STATUS      current
	DESCRIPTION "alarm severity"
::= { xfp2SeverityEntry 7 }

xfp2SeverityLowTxPower OBJECT-TYPE
	SYNTAX      Integer32
	MAX-ACCESS  read-write
	STATUS      current
	DESCRIPTION "alarm severity"
::= { xfp2SeverityEntry 8 }

xfp2SeverityHighTxPower OBJECT-TYPE
	SYNTAX      Integer32
	MAX-ACCESS  read-write
	STATUS      current
	DESCRIPTION "alarm severity"
::= { xfp2SeverityEntry 9 }

xfp2SeverityLowRxPower OBJECT-TYPE
	SYNTAX      Integer32
	MAX-ACCESS  read-write
	STATUS      current
	DESCRIPTION "alarm severity"
::= { xfp2SeverityEntry 10 }

xfp2SeverityHighRxPower OBJECT-TYPE
	SYNTAX      Integer32
	MAX-ACCESS  read-write
	STATUS      current
	DESCRIPTION "alarm severity"
::= { xfp2SeverityEntry 11 }

xfp2SeverityRxCdrLossOfLock OBJECT-TYPE
	SYNTAX      Integer32
	MAX-ACCESS  read-write
	STATUS      current
	DESCRIPTION "alarm severity"
::= { xfp2SeverityEntry 12 }

xfp2SeverityTxCdrLossOfLock OBJECT-TYPE
	SYNTAX      Integer32
	MAX-ACCESS  read-write
	STATUS      current
	DESCRIPTION "alarm severity"
::= { xfp2SeverityEntry 13 }

xfp2SeverityLaserFault OBJECT-TYPE
	SYNTAX      Integer32
	MAX-ACCESS  read-write
	STATUS      current
	DESCRIPTION "alarm severity"
::= { xfp2SeverityEntry 14 }

xfp2SeverityGroup OBJECT-GROUP
    OBJECTS { xfp2SeverityPresence, xfp2SeverityRxLoss, xfp2SeverityReady, xfp2SeverityTxPower, xfp2SeverityRxPower, 
    xfp2SeverityTemperature, xfp2SeverityLowTxPower, xfp2SeverityHighTxPower, xfp2SeverityLowRxPower, 
    xfp2SeverityHighRxPower, xfp2SeverityRxCdrLossOfLock, xfp2SeverityTxCdrLossOfLock, xfp2SeverityLaserFault }
    STATUS  current
    DESCRIPTION
        "The xfp2SeverityGroup, groups objects of xfp2Severity."
    ::= { mxpSeverityMIBGroups 4 }

--
-- Table for xfp3Severity
--
xfp3SeverityTable OBJECT-TYPE
	SYNTAX SEQUENCE OF Xfp3SeverityEntry
	MAX-ACCESS not-accessible
	STATUS current
	DESCRIPTION "A table containing information on xfp3Severity."
::= { xfpAlarms 3 }

xfp3SeverityEntry OBJECT-TYPE
	SYNTAX	Xfp3SeverityEntry
	MAX-ACCESS	not-accessible
	STATUS	current
	DESCRIPTION "An entry of the xfp3Severity table."
	INDEX	{ xfp3SeverityIndex }
::= { xfp3SeverityTable  1 }

Xfp3SeverityEntry ::= SEQUENCE { xfp3SeverityIndex Integer32, xfp3SeverityPresence Integer32, xfp3SeverityRxLoss Integer32, xfp3SeverityReady Integer32,
 xfp3SeverityTxPower Integer32, xfp3SeverityRxPower Integer32, xfp3SeverityTemperature Integer32, xfp3SeverityLowTxPower Integer32, xfp3SeverityHighTxPower Integer32, 
 xfp3SeverityLowRxPower Integer32, xfp3SeverityHighRxPower Integer32, xfp3SeverityRxCdrLossOfLock Integer32, xfp3SeverityTxCdrLossOfLock Integer32, xfp3SeverityLaserFault Integer32}

xfp3SeverityIndex OBJECT-TYPE
	SYNTAX	Integer32 (0..65535)
	MAX-ACCESS	not-accessible
	STATUS	current
	DESCRIPTION "The auxiliary variable used for identifying instances
            of the columnar objects in the xfpTable"
::= { xfp3SeverityEntry 1 }

xfp3SeverityPresence OBJECT-TYPE
	SYNTAX      Integer32
	MAX-ACCESS  read-write
	STATUS      current
	DESCRIPTION "alarm severity"
::= { xfp3SeverityEntry 2 }

xfp3SeverityRxLoss OBJECT-TYPE
	SYNTAX      Integer32
	MAX-ACCESS  read-write
	STATUS      current
	DESCRIPTION "alarm severity"
::= { xfp3SeverityEntry 3 }

xfp3SeverityReady OBJECT-TYPE
	SYNTAX      Integer32
	MAX-ACCESS  read-write
	STATUS      current
	DESCRIPTION "alarm severity"
::= { xfp3SeverityEntry 4 }

xfp3SeverityTxPower OBJECT-TYPE
	SYNTAX      Integer32
	MAX-ACCESS  read-write
	STATUS      current
	DESCRIPTION "alarm severity"
::= { xfp3SeverityEntry 5 }

xfp3SeverityRxPower OBJECT-TYPE
	SYNTAX      Integer32
	MAX-ACCESS  read-write
	STATUS      current
	DESCRIPTION "alarm severity"
::= { xfp3SeverityEntry 6 }

xfp3SeverityTemperature OBJECT-TYPE
	SYNTAX      Integer32
	MAX-ACCESS  read-write
	STATUS      current
	DESCRIPTION "alarm severity"
::= { xfp3SeverityEntry 7 }

xfp3SeverityLowTxPower OBJECT-TYPE
	SYNTAX      Integer32
	MAX-ACCESS  read-write
	STATUS      current
	DESCRIPTION "alarm severity"
::= { xfp3SeverityEntry 8 }

xfp3SeverityHighTxPower OBJECT-TYPE
	SYNTAX      Integer32
	MAX-ACCESS  read-write
	STATUS      current
	DESCRIPTION "alarm severity"
::= { xfp3SeverityEntry 9 }

xfp3SeverityLowRxPower OBJECT-TYPE
	SYNTAX      Integer32
	MAX-ACCESS  read-write
	STATUS      current
	DESCRIPTION "alarm severity"
::= { xfp3SeverityEntry 10 }

xfp3SeverityHighRxPower OBJECT-TYPE
	SYNTAX      Integer32
	MAX-ACCESS  read-write
	STATUS      current
	DESCRIPTION "alarm severity"
::= { xfp3SeverityEntry 11 }

xfp3SeverityRxCdrLossOfLock OBJECT-TYPE
	SYNTAX      Integer32
	MAX-ACCESS  read-write
	STATUS      current
	DESCRIPTION "alarm severity"
::= { xfp3SeverityEntry 12 }

xfp3SeverityTxCdrLossOfLock OBJECT-TYPE
	SYNTAX      Integer32
	MAX-ACCESS  read-write
	STATUS      current
	DESCRIPTION "alarm severity"
::= { xfp3SeverityEntry 13 }

xfp3SeverityLaserFault OBJECT-TYPE
	SYNTAX      Integer32
	MAX-ACCESS  read-write
	STATUS      current
	DESCRIPTION "alarm severity"
::= { xfp3SeverityEntry 14 }

xfp3SeverityGroup OBJECT-GROUP
    OBJECTS { xfp3SeverityPresence, xfp3SeverityRxLoss, xfp3SeverityReady, xfp3SeverityTxPower, xfp3SeverityRxPower, 
    xfp3SeverityTemperature, xfp3SeverityLowTxPower, xfp3SeverityHighTxPower, xfp3SeverityLowRxPower, 
    xfp3SeverityHighRxPower, xfp3SeverityRxCdrLossOfLock, xfp3SeverityTxCdrLossOfLock, xfp3SeverityLaserFault }
    STATUS  current
    DESCRIPTION
        "The xfp3SeverityGroup, groups objects of xfp3Severity."
    ::= { mxpSeverityMIBGroups 5 }

--
-- Table for xfp4Severity
--
xfp4SeverityTable OBJECT-TYPE
	SYNTAX SEQUENCE OF Xfp4SeverityEntry
	MAX-ACCESS not-accessible
	STATUS current
	DESCRIPTION "A table containing information on xfp4Severity."
::= { xfpAlarms 4 }

xfp4SeverityEntry OBJECT-TYPE
	SYNTAX	Xfp4SeverityEntry
	MAX-ACCESS	not-accessible
	STATUS	current
	DESCRIPTION "An entry of the xfp4Severity table."
	INDEX	{ xfp4SeverityIndex }
::= { xfp4SeverityTable  1 }

Xfp4SeverityEntry ::= SEQUENCE { xfp4SeverityIndex Integer32, xfp4SeverityPresence Integer32, xfp4SeverityRxLoss Integer32, xfp4SeverityReady Integer32,
 xfp4SeverityTxPower Integer32, xfp4SeverityRxPower Integer32, xfp4SeverityTemperature Integer32, xfp4SeverityLowTxPower Integer32, xfp4SeverityHighTxPower Integer32, 
 xfp4SeverityLowRxPower Integer32, xfp4SeverityHighRxPower Integer32, xfp4SeverityRxCdrLossOfLock Integer32, xfp4SeverityTxCdrLossOfLock Integer32, xfp4SeverityLaserFault Integer32}

xfp4SeverityIndex OBJECT-TYPE
	SYNTAX	Integer32 (0..65535)
	MAX-ACCESS	not-accessible
	STATUS	current
	DESCRIPTION "The auxiliary variable used for identifying instances
            of the columnar objects in the xfpTable"
::= { xfp4SeverityEntry 1 }

xfp4SeverityPresence OBJECT-TYPE
	SYNTAX      Integer32
	MAX-ACCESS  read-write
	STATUS      current
	DESCRIPTION "alarm severity"
::= { xfp4SeverityEntry 2 }

xfp4SeverityRxLoss OBJECT-TYPE
	SYNTAX      Integer32
	MAX-ACCESS  read-write
	STATUS      current
	DESCRIPTION "alarm severity"
::= { xfp4SeverityEntry 3 }

xfp4SeverityReady OBJECT-TYPE
	SYNTAX      Integer32
	MAX-ACCESS  read-write
	STATUS      current
	DESCRIPTION "alarm severity"
::= { xfp4SeverityEntry 4 }

xfp4SeverityTxPower OBJECT-TYPE
	SYNTAX      Integer32
	MAX-ACCESS  read-write
	STATUS      current
	DESCRIPTION "alarm severity"
::= { xfp4SeverityEntry 5 }

xfp4SeverityRxPower OBJECT-TYPE
	SYNTAX      Integer32
	MAX-ACCESS  read-write
	STATUS      current
	DESCRIPTION "alarm severity"
::= { xfp4SeverityEntry 6 }

xfp4SeverityTemperature OBJECT-TYPE
	SYNTAX      Integer32
	MAX-ACCESS  read-write
	STATUS      current
	DESCRIPTION "alarm severity"
::= { xfp4SeverityEntry 7 }

xfp4SeverityLowTxPower OBJECT-TYPE
	SYNTAX      Integer32
	MAX-ACCESS  read-write
	STATUS      current
	DESCRIPTION "alarm severity"
::= { xfp4SeverityEntry 8 }

xfp4SeverityHighTxPower OBJECT-TYPE
	SYNTAX      Integer32
	MAX-ACCESS  read-write
	STATUS      current
	DESCRIPTION "alarm severity"
::= { xfp4SeverityEntry 9 }

xfp4SeverityLowRxPower OBJECT-TYPE
	SYNTAX      Integer32
	MAX-ACCESS  read-write
	STATUS      current
	DESCRIPTION "alarm severity"
::= { xfp4SeverityEntry 10 }

xfp4SeverityHighRxPower OBJECT-TYPE
	SYNTAX      Integer32
	MAX-ACCESS  read-write
	STATUS      current
	DESCRIPTION "alarm severity"
::= { xfp4SeverityEntry 11 }

xfp4SeverityRxCdrLossOfLock OBJECT-TYPE
	SYNTAX      Integer32
	MAX-ACCESS  read-write
	STATUS      current
	DESCRIPTION "alarm severity"
::= { xfp4SeverityEntry 12 }

xfp4SeverityTxCdrLossOfLock OBJECT-TYPE
	SYNTAX      Integer32
	MAX-ACCESS  read-write
	STATUS      current
	DESCRIPTION "alarm severity"
::= { xfp4SeverityEntry 13 }

xfp4SeverityLaserFault OBJECT-TYPE
	SYNTAX      Integer32
	MAX-ACCESS  read-write
	STATUS      current
	DESCRIPTION "alarm severity"
::= { xfp4SeverityEntry 14 }

xfp4SeverityGroup OBJECT-GROUP
    OBJECTS { xfp4SeverityPresence, xfp4SeverityRxLoss, xfp4SeverityReady, xfp4SeverityTxPower, xfp4SeverityRxPower, 
    xfp4SeverityTemperature, xfp4SeverityLowTxPower, xfp4SeverityHighTxPower, xfp4SeverityLowRxPower, 
    xfp4SeverityHighRxPower, xfp4SeverityRxCdrLossOfLock, xfp4SeverityTxCdrLossOfLock, xfp4SeverityLaserFault }
    STATUS  current
    DESCRIPTION
        "The xfp4SeverityGroup, groups objects of xfp4Severity."
    ::= { mxpSeverityMIBGroups 6 }


--
-- Table for traffic processor line
--
tpLineSeverityTable OBJECT-TYPE
	SYNTAX SEQUENCE OF TpLineSeverityEntry
	MAX-ACCESS not-accessible
	STATUS current
	DESCRIPTION "A table containing information on tpLineSeverity."
::= { tpAlarms 1 }

tpLineSeverityEntry OBJECT-TYPE
	SYNTAX	TpLineSeverityEntry
	MAX-ACCESS	not-accessible
	STATUS	current
	DESCRIPTION "An entry of the tpLineSeverity table."
	INDEX	{ tpLineSeverityIndex }
::= { tpLineSeverityTable  1 }

TpLineSeverityEntry ::= SEQUENCE { tpLineSeverityIndex Integer32, tpLineSeverityFramerFsmms Integer32, tpLineSeverityFramerFsmmtrb1s Integer32
, tpLineSeverityFramerFsmmtrb2s Integer32, tpLineSeverityFramerFsmmtrb3s Integer32, tpLineSeverityFramerSoof Integer32, tpLineSeverityFramerSlof Integer32
, tpLineSeverityFramerSif Integer32, tpLineSeverityFramerFst Integer32, tpLineSeverityLosstatLosf Integer32, tpLineSeverityPathmonAccstat Integer32, tpLineSeverityPathmonDais Integer32
, tpLineSeverityPathmonDbdi Integer32, tpLineSeverityPathmonDlck Integer32, tpLineSeverityPathmonMsiunst Integer32, tpLineSeveritySecmonBipsfs Integer32
, tpLineSeveritySecmonDbdi Integer32, tpLineSeveritySecmonDiae Integer32, tpLineSeveritySecmonFlom Integer32, tpLineSeveritySecmonLom Integer32}

tpLineSeverityIndex OBJECT-TYPE
	SYNTAX	Integer32 (0..65535)
	MAX-ACCESS	not-accessible
	STATUS	current
	DESCRIPTION "The auxiliary variable used for identifying instances
            of the columnar objects in the tpTable"
::= { tpLineSeverityEntry 1 }

tpLineSeverityFramerFsmms OBJECT-TYPE
	SYNTAX      Integer32
	MAX-ACCESS  read-write
	STATUS      current
	DESCRIPTION "alarm severity"
::= { tpLineSeverityEntry 2 }

tpLineSeverityFramerFsmmtrb1s OBJECT-TYPE
	SYNTAX      Integer32
	MAX-ACCESS  read-write
	STATUS      current
	DESCRIPTION "alarm severity"
::= { tpLineSeverityEntry 3 }

tpLineSeverityFramerFsmmtrb2s OBJECT-TYPE
	SYNTAX      Integer32
	MAX-ACCESS  read-write
	STATUS      current
	DESCRIPTION "alarm severity"
::= { tpLineSeverityEntry 4 }

tpLineSeverityFramerFsmmtrb3s OBJECT-TYPE
	SYNTAX      Integer32
	MAX-ACCESS  read-write
	STATUS      current
	DESCRIPTION "alarm severity"
::= { tpLineSeverityEntry 5 }

tpLineSeverityFramerSoof OBJECT-TYPE
	SYNTAX      Integer32
	MAX-ACCESS  read-write
	STATUS      current
	DESCRIPTION "alarm severity"
::= { tpLineSeverityEntry 6 }

tpLineSeverityFramerSlof OBJECT-TYPE
	SYNTAX      Integer32
	MAX-ACCESS  read-write
	STATUS      current
	DESCRIPTION "alarm severity"
::= { tpLineSeverityEntry 7 }

tpLineSeverityFramerSif OBJECT-TYPE
	SYNTAX      Integer32
	MAX-ACCESS  read-write
	STATUS      current
	DESCRIPTION "alarm severity"
::= { tpLineSeverityEntry 8 }

tpLineSeverityFramerFst OBJECT-TYPE
	SYNTAX      Integer32
	MAX-ACCESS  read-write
	STATUS      current
	DESCRIPTION "alarm severity"
::= { tpLineSeverityEntry 9 }

tpLineSeverityLosstatLosf OBJECT-TYPE
	SYNTAX      Integer32
	MAX-ACCESS  read-write
	STATUS      current
	DESCRIPTION "alarm severity"
::= { tpLineSeverityEntry 10 }

tpLineSeverityPathmonAccstat OBJECT-TYPE
	SYNTAX      Integer32
	MAX-ACCESS  read-write
	STATUS      current
	DESCRIPTION "alarm severity"
::= { tpLineSeverityEntry 11 }

tpLineSeverityPathmonDais OBJECT-TYPE
	SYNTAX      Integer32
	MAX-ACCESS  read-write
	STATUS      current
	DESCRIPTION "alarm severity"
::= { tpLineSeverityEntry 12 }

tpLineSeverityPathmonDbdi OBJECT-TYPE
	SYNTAX      Integer32
	MAX-ACCESS  read-write
	STATUS      current
	DESCRIPTION "alarm severity"
::= { tpLineSeverityEntry 13 }

tpLineSeverityPathmonDlck OBJECT-TYPE
	SYNTAX      Integer32
	MAX-ACCESS  read-write
	STATUS      current
	DESCRIPTION "alarm severity"
::= { tpLineSeverityEntry 14 }

tpLineSeverityPathmonMsiunst OBJECT-TYPE
	SYNTAX      Integer32
	MAX-ACCESS  read-write
	STATUS      current
	DESCRIPTION "alarm severity"
::= { tpLineSeverityEntry 15 }

tpLineSeveritySecmonBipsfs OBJECT-TYPE
	SYNTAX      Integer32
	MAX-ACCESS  read-write
	STATUS      current
	DESCRIPTION "alarm severity"
::= { tpLineSeverityEntry 16 }

tpLineSeveritySecmonDbdi OBJECT-TYPE
	SYNTAX      Integer32
	MAX-ACCESS  read-write
	STATUS      current
	DESCRIPTION "alarm severity"
::= { tpLineSeverityEntry 17 }

tpLineSeveritySecmonDiae OBJECT-TYPE
	SYNTAX      Integer32
	MAX-ACCESS  read-write
	STATUS      current
	DESCRIPTION "alarm severity"
::= { tpLineSeverityEntry 18 }

tpLineSeveritySecmonFlom OBJECT-TYPE
	SYNTAX      Integer32
	MAX-ACCESS  read-write
	STATUS      current
	DESCRIPTION "alarm severity"
::= { tpLineSeverityEntry 19 }

tpLineSeveritySecmonLom OBJECT-TYPE
	SYNTAX      Integer32
	MAX-ACCESS  read-write
	STATUS      current
	DESCRIPTION "alarm severity"
::= { tpLineSeverityEntry 20 }

tpLineSeverityGroup OBJECT-GROUP
    OBJECTS { tpLineSeverityFramerFsmms, tpLineSeverityFramerFsmmtrb1s, tpLineSeverityFramerFsmmtrb2s, tpLineSeverityFramerFsmmtrb3s, 
    tpLineSeverityFramerSoof, tpLineSeverityFramerSlof, tpLineSeverityFramerSif, tpLineSeverityFramerFst, tpLineSeverityLosstatLosf, tpLineSeverityPathmonAccstat, 
    tpLineSeverityPathmonDais, tpLineSeverityPathmonDbdi, tpLineSeverityPathmonDlck, tpLineSeverityPathmonMsiunst, tpLineSeveritySecmonBipsfs, 
    tpLineSeveritySecmonDbdi, tpLineSeveritySecmonDiae, tpLineSeveritySecmonFlom, tpLineSeveritySecmonLom}
    STATUS  current
    DESCRIPTION
        "The tpLineSeverityGroup, groups objects of tpLineSeverity."
    ::= { mxpSeverityMIBGroups 7 }


--
-- Table for traffic processor client1
--

tpClient1SeverityTable OBJECT-TYPE
	SYNTAX SEQUENCE OF TpClient1SeverityEntry
	MAX-ACCESS not-accessible
	STATUS current
	DESCRIPTION "A table containing information on tpClient1Severity."
::= { tpAlarms 2 }

tpClient1SeverityEntry OBJECT-TYPE
	SYNTAX	TpClient1SeverityEntry
	MAX-ACCESS	not-accessible
	STATUS	current
	DESCRIPTION "An entry of the tpClient1severity table."
	INDEX	{ tpClient1SeverityIndex }
::= { tpClient1SeverityTable  1 }

TpClient1SeverityEntry ::= SEQUENCE { tpClient1SeverityIndex Integer32,tpClient1SeverityFramerFsmms Integer32, tpClient1SeverityFramerFssusts Integer32, tpClient1SeverityFramerSoof Integer32
, tpClient1SeverityFramerSlof Integer32, tpClient1SeverityFramerSif Integer32, tpClient1SeverityFramerFst Integer32, tpClient1SeverityLosstatLosf Integer32, tpClient1SeverityPathmonAccstat Integer32
, tpClient1SeverityPathmonDais Integer32, tpClient1SeverityPathmonDbdi Integer32, tpClient1SeverityPathmonDlck Integer32, tpClient1SeverityPathmonMsiunst Integer32
, tpClient1SeveritySecmonBipsfs Integer32, tpClient1SeveritySecmonDbdi Integer32, tpClient1SeveritySecmonDiae Integer32, tpClient1SeveritySecmonFlom Integer32
, tpClient1SeveritySecmonLom Integer32}

tpClient1SeverityIndex OBJECT-TYPE
	SYNTAX	Integer32 (0..65535)
	MAX-ACCESS	not-accessible
	STATUS	current
	DESCRIPTION "The auxiliary variable used for identifying instances
            of the columnar objects in the tpTable"
::= { tpClient1SeverityEntry 1 }

tpClient1SeverityFramerFsmms OBJECT-TYPE
	SYNTAX      Integer32
	MAX-ACCESS  read-write
	STATUS      current
	DESCRIPTION "alarm severity"
::= { tpClient1SeverityEntry 2 }

tpClient1SeverityFramerFssusts OBJECT-TYPE
	SYNTAX      Integer32
	MAX-ACCESS  read-write
	STATUS      current
	DESCRIPTION "alarm severity"
::= { tpClient1SeverityEntry 3 }

tpClient1SeverityFramerSoof OBJECT-TYPE
	SYNTAX      Integer32
	MAX-ACCESS  read-write
	STATUS      current
	DESCRIPTION "alarm severity"
::= { tpClient1SeverityEntry 4 }

tpClient1SeverityFramerSlof OBJECT-TYPE
	SYNTAX      Integer32
	MAX-ACCESS  read-write
	STATUS      current
	DESCRIPTION "alarm severity"
::= { tpClient1SeverityEntry 5 }

tpClient1SeverityFramerSif OBJECT-TYPE
	SYNTAX      Integer32
	MAX-ACCESS  read-write
	STATUS      current
	DESCRIPTION "alarm severity"
::= { tpClient1SeverityEntry 6 }

tpClient1SeverityFramerFst OBJECT-TYPE
	SYNTAX      Integer32
	MAX-ACCESS  read-write
	STATUS      current
	DESCRIPTION "alarm severity"
::= { tpClient1SeverityEntry 7 }

tpClient1SeverityLosstatLosf OBJECT-TYPE
	SYNTAX      Integer32
	MAX-ACCESS  read-write
	STATUS      current
	DESCRIPTION "alarm severity"
::= { tpClient1SeverityEntry 8 }

tpClient1SeverityPathmonAccstat OBJECT-TYPE
	SYNTAX      Integer32
	MAX-ACCESS  read-write
	STATUS      current
	DESCRIPTION "alarm severity"
::= { tpClient1SeverityEntry 9 }

tpClient1SeverityPathmonDais OBJECT-TYPE
	SYNTAX      Integer32
	MAX-ACCESS  read-write
	STATUS      current
	DESCRIPTION "alarm severity"
::= { tpClient1SeverityEntry 10 }

tpClient1SeverityPathmonDbdi OBJECT-TYPE
	SYNTAX      Integer32
	MAX-ACCESS  read-write
	STATUS      current
	DESCRIPTION "alarm severity"
::= { tpClient1SeverityEntry 11 }

tpClient1SeverityPathmonDlck OBJECT-TYPE
	SYNTAX      Integer32
	MAX-ACCESS  read-write
	STATUS      current
	DESCRIPTION "alarm severity"
::= { tpClient1SeverityEntry 12 }

tpClient1SeverityPathmonMsiunst OBJECT-TYPE
	SYNTAX      Integer32
	MAX-ACCESS  read-write
	STATUS      current
	DESCRIPTION "alarm severity"
::= { tpClient1SeverityEntry 13 }

tpClient1SeveritySecmonBipsfs OBJECT-TYPE
	SYNTAX      Integer32
	MAX-ACCESS  read-write
	STATUS      current
	DESCRIPTION "alarm severity"
::= { tpClient1SeverityEntry 14 }

tpClient1SeveritySecmonDbdi OBJECT-TYPE
	SYNTAX      Integer32
	MAX-ACCESS  read-write
	STATUS      current
	DESCRIPTION "alarm severity"
::= { tpClient1SeverityEntry 15 }

tpClient1SeveritySecmonDiae OBJECT-TYPE
	SYNTAX      Integer32
	MAX-ACCESS  read-write
	STATUS      current
	DESCRIPTION "alarm severity"
::= { tpClient1SeverityEntry 16 }

tpClient1SeveritySecmonFlom OBJECT-TYPE
	SYNTAX      Integer32
	MAX-ACCESS  read-write
	STATUS      current
	DESCRIPTION "alarm severity"
::= { tpClient1SeverityEntry 17 }

tpClient1SeveritySecmonLom OBJECT-TYPE
	SYNTAX      Integer32
	MAX-ACCESS  read-write
	STATUS      current
	DESCRIPTION "alarm severity"
::= { tpClient1SeverityEntry 18 }

tpClient1SeverityGroup OBJECT-GROUP
    OBJECTS { tpClient1SeverityFramerFsmms, tpClient1SeverityFramerFssusts, tpClient1SeverityFramerSoof, tpClient1SeverityFramerSlof, 
    tpClient1SeverityFramerSif,tpClient1SeverityFramerFst, tpClient1SeverityLosstatLosf, tpClient1SeverityPathmonAccstat, tpClient1SeverityPathmonDais, 
    tpClient1SeverityPathmonDbdi, tpClient1SeverityPathmonDlck, tpClient1SeverityPathmonMsiunst, tpClient1SeveritySecmonBipsfs, 
    tpClient1SeveritySecmonDbdi, tpClient1SeveritySecmonDiae, tpClient1SeveritySecmonFlom, tpClient1SeveritySecmonLom}
    STATUS  current
    DESCRIPTION
        "The tpClient1SeverityGroup, groups objects of tpClient1Severity."
    ::= { mxpSeverityMIBGroups 8 }


--
-- Table for traffic processor client2
--
tpClient2SeverityTable OBJECT-TYPE
	SYNTAX SEQUENCE OF TpClient2SeverityEntry
	MAX-ACCESS not-accessible
	STATUS current
	DESCRIPTION "A table containing information on tpClient2Severity."
::= { tpAlarms 3 }

tpClient2SeverityEntry OBJECT-TYPE
	SYNTAX	TpClient2SeverityEntry
	MAX-ACCESS	not-accessible
	STATUS	current
	DESCRIPTION "An entry of the tpLtpClient2erity table."
	INDEX	{ tpClient2SeverityIndex }
::= { tpClient2SeverityTable  1 }

TpClient2SeverityEntry ::= SEQUENCE { tpClient2SeverityIndex Integer32,tpClient2SeverityFramerFsmms Integer32, tpClient2SeverityFramerFssusts Integer32, tpClient2SeverityFramerSoof Integer32
, tpClient2SeverityFramerSlof Integer32, tpClient2SeverityFramerSif Integer32,tpClient2SeverityFramerFst Integer32, tpClient2SeverityLosstatLosf Integer32, tpClient2SeverityPathmonAccstat Integer32
, tpClient2SeverityPathmonDais Integer32, tpClient2SeverityPathmonDbdi Integer32, tpClient2SeverityPathmonDlck Integer32, tpClient2SeverityPathmonMsiunst Integer32
, tpClient2SeveritySecmonBipsfs Integer32, tpClient2SeveritySecmonDbdi Integer32, tpClient2SeveritySecmonDiae Integer32, tpClient2SeveritySecmonFlom Integer32
, tpClient2SeveritySecmonLom Integer32}

tpClient2SeverityIndex OBJECT-TYPE
	SYNTAX	Integer32 (0..65535)
	MAX-ACCESS	not-accessible
	STATUS	current
	DESCRIPTION "The auxiliary variable used for identifying instances
            of the columnar objects in the tpTable"
::= { tpClient2SeverityEntry 1 }

tpClient2SeverityFramerFsmms OBJECT-TYPE
	SYNTAX      Integer32
	MAX-ACCESS  read-write
	STATUS      current
	DESCRIPTION "alarm severity"
::= { tpClient2SeverityEntry 2 }

tpClient2SeverityFramerFssusts OBJECT-TYPE
	SYNTAX      Integer32
	MAX-ACCESS  read-write
	STATUS      current
	DESCRIPTION "alarm severity"
::= { tpClient2SeverityEntry 3 }

tpClient2SeverityFramerSoof OBJECT-TYPE
	SYNTAX      Integer32
	MAX-ACCESS  read-write
	STATUS      current
	DESCRIPTION "alarm severity"
::= { tpClient2SeverityEntry 4 }

tpClient2SeverityFramerSlof OBJECT-TYPE
	SYNTAX      Integer32
	MAX-ACCESS  read-write
	STATUS      current
	DESCRIPTION "alarm severity"
::= { tpClient2SeverityEntry 5 }

tpClient2SeverityFramerSif OBJECT-TYPE
	SYNTAX      Integer32
	MAX-ACCESS  read-write
	STATUS      current
	DESCRIPTION "alarm severity"
::= { tpClient2SeverityEntry 6 }

tpClient2SeverityFramerFst OBJECT-TYPE
	SYNTAX      Integer32
	MAX-ACCESS  read-write
	STATUS      current
	DESCRIPTION "alarm severity"
::= { tpClient2SeverityEntry 7 }

tpClient2SeverityLosstatLosf OBJECT-TYPE
	SYNTAX      Integer32
	MAX-ACCESS  read-write
	STATUS      current
	DESCRIPTION "alarm severity"
::= { tpClient2SeverityEntry 8 }

tpClient2SeverityPathmonAccstat OBJECT-TYPE
	SYNTAX      Integer32
	MAX-ACCESS  read-write
	STATUS      current
	DESCRIPTION "alarm severity"
::= { tpClient2SeverityEntry 9 }

tpClient2SeverityPathmonDais OBJECT-TYPE
	SYNTAX      Integer32
	MAX-ACCESS  read-write
	STATUS      current
	DESCRIPTION "alarm severity"
::= { tpClient2SeverityEntry 10 }

tpClient2SeverityPathmonDbdi OBJECT-TYPE
	SYNTAX      Integer32
	MAX-ACCESS  read-write
	STATUS      current
	DESCRIPTION "alarm severity"
::= { tpClient2SeverityEntry 11 }

tpClient2SeverityPathmonDlck OBJECT-TYPE
	SYNTAX      Integer32
	MAX-ACCESS  read-write
	STATUS      current
	DESCRIPTION "alarm severity"
::= { tpClient2SeverityEntry 12 }

tpClient2SeverityPathmonMsiunst OBJECT-TYPE
	SYNTAX      Integer32
	MAX-ACCESS  read-write
	STATUS      current
	DESCRIPTION "alarm severity"
::= { tpClient2SeverityEntry 13 }

tpClient2SeveritySecmonBipsfs OBJECT-TYPE
	SYNTAX      Integer32
	MAX-ACCESS  read-write
	STATUS      current
	DESCRIPTION "alarm severity"
::= { tpClient2SeverityEntry 14 }

tpClient2SeveritySecmonDbdi OBJECT-TYPE
	SYNTAX      Integer32
	MAX-ACCESS  read-write
	STATUS      current
	DESCRIPTION "alarm severity"
::= { tpClient2SeverityEntry 15 }

tpClient2SeveritySecmonDiae OBJECT-TYPE
	SYNTAX      Integer32
	MAX-ACCESS  read-write
	STATUS      current
	DESCRIPTION "alarm severity"
::= { tpClient2SeverityEntry 16 }

tpClient2SeveritySecmonFlom OBJECT-TYPE
	SYNTAX      Integer32
	MAX-ACCESS  read-write
	STATUS      current
	DESCRIPTION "alarm severity"
::= { tpClient2SeverityEntry 17 }

tpClient2SeveritySecmonLom OBJECT-TYPE
	SYNTAX      Integer32
	MAX-ACCESS  read-write
	STATUS      current
	DESCRIPTION "alarm severity"
::= { tpClient2SeverityEntry 18 }

tpClient2SeverityGroup OBJECT-GROUP
    OBJECTS { tpClient2SeverityFramerFsmms, tpClient2SeverityFramerFssusts, tpClient2SeverityFramerSoof, tpClient2SeverityFramerSlof, 
    tpClient2SeverityFramerFst, tpClient2SeverityFramerSif, tpClient2SeverityLosstatLosf, tpClient2SeverityPathmonAccstat, tpClient2SeverityPathmonDais, 
    tpClient2SeverityPathmonDbdi, tpClient2SeverityPathmonDlck, tpClient2SeverityPathmonMsiunst, tpClient2SeveritySecmonBipsfs, 
    tpClient2SeveritySecmonDbdi, tpClient2SeveritySecmonDiae, tpClient2SeveritySecmonFlom, tpClient2SeveritySecmonLom}
    STATUS  current
    DESCRIPTION
        "The tpClient2SeverityGroup, groups objects of tpClient2Severity."
    ::= { mxpSeverityMIBGroups 9 }
    

--
-- Table for traffic processor client3
--

tpClient3SeverityTable OBJECT-TYPE
	SYNTAX SEQUENCE OF TpClient3SeverityEntry
	MAX-ACCESS not-accessible
	STATUS current
	DESCRIPTION "A table containing information on tpClient3Severity."
::= { tpAlarms 4 }

tpClient3SeverityEntry OBJECT-TYPE
	SYNTAX	TpClient3SeverityEntry
	MAX-ACCESS	not-accessible
	STATUS	current
	DESCRIPTION "An entry of the tpLtpClient3erity table."
	INDEX	{ tpClient3SeverityIndex }
::= { tpClient3SeverityTable  1 }

TpClient3SeverityEntry ::= SEQUENCE { tpClient3SeverityIndex Integer32,tpClient3SeverityFramerFsmms Integer32, tpClient3SeverityFramerFssusts Integer32, tpClient3SeverityFramerSoof Integer32
, tpClient3SeverityFramerSlof Integer32, tpClient3SeverityFramerSif Integer32, tpClient3SeverityFramerFst Integer32, tpClient3SeverityLosstatLosf Integer32, tpClient3SeverityPathmonAccstat Integer32
, tpClient3SeverityPathmonDais Integer32, tpClient3SeverityPathmonDbdi Integer32, tpClient3SeverityPathmonDlck Integer32, tpClient3SeverityPathmonMsiunst Integer32
, tpClient3SeveritySecmonBipsfs Integer32, tpClient3SeveritySecmonDbdi Integer32, tpClient3SeveritySecmonDiae Integer32, tpClient3SeveritySecmonFlom Integer32
, tpClient3SeveritySecmonLom Integer32}

tpClient3SeverityIndex OBJECT-TYPE
	SYNTAX	Integer32 (0..65535)
	MAX-ACCESS	not-accessible
	STATUS	current
	DESCRIPTION "The auxiliary variable used for identifying instances
            of the columnar objects in the tpTable"
::= { tpClient3SeverityEntry 1 }

tpClient3SeverityFramerFsmms OBJECT-TYPE
	SYNTAX      Integer32
	MAX-ACCESS  read-write
	STATUS      current
	DESCRIPTION "alarm severity"
::= { tpClient3SeverityEntry 2 }

tpClient3SeverityFramerFssusts OBJECT-TYPE
	SYNTAX      Integer32
	MAX-ACCESS  read-write
	STATUS      current
	DESCRIPTION "alarm severity"
::= { tpClient3SeverityEntry 3 }

tpClient3SeverityFramerSoof OBJECT-TYPE
	SYNTAX      Integer32
	MAX-ACCESS  read-write
	STATUS      current
	DESCRIPTION "alarm severity"
::= { tpClient3SeverityEntry 4 }

tpClient3SeverityFramerSlof OBJECT-TYPE
	SYNTAX      Integer32
	MAX-ACCESS  read-write
	STATUS      current
	DESCRIPTION "alarm severity"
::= { tpClient3SeverityEntry 5 }

tpClient3SeverityFramerSif OBJECT-TYPE
	SYNTAX      Integer32
	MAX-ACCESS  read-write
	STATUS      current
	DESCRIPTION "alarm severity"
::= { tpClient3SeverityEntry 6 }

tpClient3SeverityFramerFst OBJECT-TYPE
	SYNTAX      Integer32
	MAX-ACCESS  read-write
	STATUS      current
	DESCRIPTION "alarm severity"
::= { tpClient3SeverityEntry 7 }

tpClient3SeverityLosstatLosf OBJECT-TYPE
	SYNTAX      Integer32
	MAX-ACCESS  read-write
	STATUS      current
	DESCRIPTION "alarm severity"
::= { tpClient3SeverityEntry 8 }

tpClient3SeverityPathmonAccstat OBJECT-TYPE
	SYNTAX      Integer32
	MAX-ACCESS  read-write
	STATUS      current
	DESCRIPTION "alarm severity"
::= { tpClient3SeverityEntry 9 }

tpClient3SeverityPathmonDais OBJECT-TYPE
	SYNTAX      Integer32
	MAX-ACCESS  read-write
	STATUS      current
	DESCRIPTION "alarm severity"
::= { tpClient3SeverityEntry 10 }

tpClient3SeverityPathmonDbdi OBJECT-TYPE
	SYNTAX      Integer32
	MAX-ACCESS  read-write
	STATUS      current
	DESCRIPTION "alarm severity"
::= { tpClient3SeverityEntry 11 }

tpClient3SeverityPathmonDlck OBJECT-TYPE
	SYNTAX      Integer32
	MAX-ACCESS  read-write
	STATUS      current
	DESCRIPTION "alarm severity"
::= { tpClient3SeverityEntry 12 }

tpClient3SeverityPathmonMsiunst OBJECT-TYPE
	SYNTAX      Integer32
	MAX-ACCESS  read-write
	STATUS      current
	DESCRIPTION "alarm severity"
::= { tpClient3SeverityEntry 13 }

tpClient3SeveritySecmonBipsfs OBJECT-TYPE
	SYNTAX      Integer32
	MAX-ACCESS  read-write
	STATUS      current
	DESCRIPTION "alarm severity"
::= { tpClient3SeverityEntry 14 }

tpClient3SeveritySecmonDbdi OBJECT-TYPE
	SYNTAX      Integer32
	MAX-ACCESS  read-write
	STATUS      current
	DESCRIPTION "alarm severity"
::= { tpClient3SeverityEntry 15 }

tpClient3SeveritySecmonDiae OBJECT-TYPE
	SYNTAX      Integer32
	MAX-ACCESS  read-write
	STATUS      current
	DESCRIPTION "alarm severity"
::= { tpClient3SeverityEntry 16 }

tpClient3SeveritySecmonFlom OBJECT-TYPE
	SYNTAX      Integer32
	MAX-ACCESS  read-write
	STATUS      current
	DESCRIPTION "alarm severity"
::= { tpClient3SeverityEntry 17 }

tpClient3SeveritySecmonLom OBJECT-TYPE
	SYNTAX      Integer32
	MAX-ACCESS  read-write
	STATUS      current
	DESCRIPTION "alarm severity"
::= { tpClient3SeverityEntry 18 }

tpClient3SeverityGroup OBJECT-GROUP
    OBJECTS { tpClient3SeverityFramerFsmms, tpClient3SeverityFramerFssusts, tpClient3SeverityFramerSoof, tpClient3SeverityFramerSlof, 
    tpClient3SeverityFramerFst, tpClient3SeverityFramerSif, tpClient3SeverityLosstatLosf, tpClient3SeverityPathmonAccstat, tpClient3SeverityPathmonDais, 
    tpClient3SeverityPathmonDbdi, tpClient3SeverityPathmonDlck, tpClient3SeverityPathmonMsiunst, tpClient3SeveritySecmonBipsfs, 
    tpClient3SeveritySecmonDbdi, tpClient3SeveritySecmonDiae, tpClient3SeveritySecmonFlom, tpClient3SeveritySecmonLom}
    STATUS  current
    DESCRIPTION
        "The tpClient3SeverityGroup, groups objects of tpClient3Severity."
    ::= { mxpSeverityMIBGroups 10 }


--
-- Table for traffic processor client4
--

tpClient4SeverityTable OBJECT-TYPE
	SYNTAX SEQUENCE OF TpClient4SeverityEntry
	MAX-ACCESS not-accessible
	STATUS current
	DESCRIPTION "A table containing information on tpClient4Severity."
::= { tpAlarms 5 }

tpClient4SeverityEntry OBJECT-TYPE
	SYNTAX	TpClient4SeverityEntry
	MAX-ACCESS	not-accessible
	STATUS	current
	DESCRIPTION "An entry of the tpLtpClient4erity table."
	INDEX	{ tpClient4SeverityIndex }
::= { tpClient4SeverityTable  1 }

TpClient4SeverityEntry ::= SEQUENCE { tpClient4SeverityIndex Integer32,tpClient4SeverityFramerFsmms Integer32, tpClient4SeverityFramerFssusts Integer32, tpClient4SeverityFramerSoof Integer32
, tpClient4SeverityFramerSlof Integer32, tpClient4SeverityFramerSif Integer32, tpClient4SeverityFramerFst Integer32, tpClient4SeverityLosstatLosf Integer32, tpClient4SeverityPathmonAccstat Integer32
, tpClient4SeverityPathmonDais Integer32, tpClient4SeverityPathmonDbdi Integer32, tpClient4SeverityPathmonDlck Integer32, tpClient4SeverityPathmonMsiunst Integer32
, tpClient4SeveritySecmonBipsfs Integer32, tpClient4SeveritySecmonDbdi Integer32, tpClient4SeveritySecmonDiae Integer32, tpClient4SeveritySecmonFlom Integer32
, tpClient4SeveritySecmonLom Integer32}

tpClient4SeverityIndex OBJECT-TYPE
	SYNTAX	Integer32 (0..65535)
	MAX-ACCESS	not-accessible
	STATUS	current
	DESCRIPTION "The auxiliary variable used for identifying instances
            of the columnar objects in the tpTable"
::= { tpClient4SeverityEntry 1 }

tpClient4SeverityFramerFsmms OBJECT-TYPE
	SYNTAX      Integer32
	MAX-ACCESS  read-write
	STATUS      current
	DESCRIPTION "alarm severity"
::= { tpClient4SeverityEntry 2 }

tpClient4SeverityFramerFssusts OBJECT-TYPE
	SYNTAX      Integer32
	MAX-ACCESS  read-write
	STATUS      current
	DESCRIPTION "alarm severity"
::= { tpClient4SeverityEntry 3 }

tpClient4SeverityFramerSoof OBJECT-TYPE
	SYNTAX      Integer32
	MAX-ACCESS  read-write
	STATUS      current
	DESCRIPTION "alarm severity"
::= { tpClient4SeverityEntry 4 }

tpClient4SeverityFramerSlof OBJECT-TYPE
	SYNTAX      Integer32
	MAX-ACCESS  read-write
	STATUS      current
	DESCRIPTION "alarm severity"
::= { tpClient4SeverityEntry 5 }

tpClient4SeverityFramerSif OBJECT-TYPE
	SYNTAX      Integer32
	MAX-ACCESS  read-write
	STATUS      current
	DESCRIPTION "alarm severity"
::= { tpClient4SeverityEntry 6 }

tpClient4SeverityFramerFst OBJECT-TYPE
	SYNTAX      Integer32
	MAX-ACCESS  read-write
	STATUS      current
	DESCRIPTION "alarm severity"
::= { tpClient4SeverityEntry 7 }

tpClient4SeverityLosstatLosf OBJECT-TYPE
	SYNTAX      Integer32
	MAX-ACCESS  read-write
	STATUS      current
	DESCRIPTION "alarm severity"
::= { tpClient4SeverityEntry 8 }

tpClient4SeverityPathmonAccstat OBJECT-TYPE
	SYNTAX      Integer32
	MAX-ACCESS  read-write
	STATUS      current
	DESCRIPTION "alarm severity"
::= { tpClient4SeverityEntry 9 }

tpClient4SeverityPathmonDais OBJECT-TYPE
	SYNTAX      Integer32
	MAX-ACCESS  read-write
	STATUS      current
	DESCRIPTION "alarm severity"
::= { tpClient4SeverityEntry 10 }

tpClient4SeverityPathmonDbdi OBJECT-TYPE
	SYNTAX      Integer32
	MAX-ACCESS  read-write
	STATUS      current
	DESCRIPTION "alarm severity"
::= { tpClient4SeverityEntry 11 }

tpClient4SeverityPathmonDlck OBJECT-TYPE
	SYNTAX      Integer32
	MAX-ACCESS  read-write
	STATUS      current
	DESCRIPTION "alarm severity"
::= { tpClient4SeverityEntry 12 }

tpClient4SeverityPathmonMsiunst OBJECT-TYPE
	SYNTAX      Integer32
	MAX-ACCESS  read-write
	STATUS      current
	DESCRIPTION "alarm severity"
::= { tpClient4SeverityEntry 13 }

tpClient4SeveritySecmonBipsfs OBJECT-TYPE
	SYNTAX      Integer32
	MAX-ACCESS  read-write
	STATUS      current
	DESCRIPTION "alarm severity"
::= { tpClient4SeverityEntry 14 }

tpClient4SeveritySecmonDbdi OBJECT-TYPE
	SYNTAX      Integer32
	MAX-ACCESS  read-write
	STATUS      current
	DESCRIPTION "alarm severity"
::= { tpClient4SeverityEntry 15 }

tpClient4SeveritySecmonDiae OBJECT-TYPE
	SYNTAX      Integer32
	MAX-ACCESS  read-write
	STATUS      current
	DESCRIPTION "alarm severity"
::= { tpClient4SeverityEntry 16 }

tpClient4SeveritySecmonFlom OBJECT-TYPE
	SYNTAX      Integer32
	MAX-ACCESS  read-write
	STATUS      current
	DESCRIPTION "alarm severity"
::= { tpClient4SeverityEntry 17 }

tpClient4SeveritySecmonLom OBJECT-TYPE
	SYNTAX      Integer32
	MAX-ACCESS  read-write
	STATUS      current
	DESCRIPTION "alarm severity"
::= { tpClient4SeverityEntry 18 }

tpClient4SeverityGroup OBJECT-GROUP
    OBJECTS { tpClient4SeverityFramerFsmms, tpClient4SeverityFramerFssusts, tpClient4SeverityFramerSoof, tpClient4SeverityFramerSlof, 
    tpClient4SeverityFramerSif,tpClient4SeverityFramerFst, tpClient4SeverityLosstatLosf, tpClient4SeverityPathmonAccstat, tpClient4SeverityPathmonDais, 
    tpClient4SeverityPathmonDbdi, tpClient4SeverityPathmonDlck, tpClient4SeverityPathmonMsiunst, tpClient4SeveritySecmonBipsfs, 
    tpClient4SeveritySecmonDbdi, tpClient4SeveritySecmonDiae, tpClient4SeveritySecmonFlom, tpClient4SeveritySecmonLom}
    STATUS  current
    DESCRIPTION
        "The tpClient4SeverityGroup, groups objects of tpClient4Severity."
    ::= { mxpSeverityMIBGroups 11 }

END
